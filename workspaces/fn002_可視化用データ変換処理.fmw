FME workspace fn002_可視化用データ変換処理.fmw

Parameters:
- GRP_INPUT =   # SourceDataset_POSTGRES 入力
- SourceDataset_POSTGRES = postgresql-plateau-park-management   # 公園施設管理データベース (PostgreSQL)
- GRP_RESOURCES =   # リソース
- SourceDataset_XLSXR = $(FME_MF_DIR_USERTYPED)fn002_resources\概形3Dモデル調整パラメーター.xlsx   # 概形3Dモデル調整パラメーター (Excel)
- SourceDataset_OBJ_3 = ""$(FME_MF_DIR_USERTYPED)fn002_resources\概形3Dモデル_看板\kanbanA.obj" "$(FME_MF_DIR_USERTYPED)fn002_resources\概形3Dモデル_看板\kanbanB.obj" "$(FME_MF_DIR_USERTYPED)fn002_resources\概形3Dモデル_看板\kanbanC.obj" "$(FME_MF_DIR_USERTYPED)fn002_resources\概形3Dモデル_看板\kanbanD.obj" "$(FME_MF_DIR_USERTYPED)fn002_resources\概形3Dモデル_看板\kanbanE.obj""   # 概形3Dモデル 看板 (OBJ)
- SourceDataset_OBJ = ""$(FME_MF_DIR_USERTYPED)fn002_resources\概形3Dモデル_樹木\3_樹種不明.obj" "$(FME_MF_DIR_USERTYPED)fn002_resources\概形3Dモデル_樹木\1_広葉樹.obj" "$(FME_MF_DIR_USERTYPED)fn002_resources\概形3Dモデル_樹木\2_針葉樹.obj""   # 概形3Dモデル 樹木 (OBJ)
- SourceDataset_GEOTIFF = $(FME_MF_DIR_USERTYPED)fn002_resources\数値地形モデル\*.tif   # 数値地形モデル (GeoTIFF)
- GEOID_HEIGHT_GRID = $(FME_MF_DIR_USERTYPED)fn002_resources\gsigeo2011\gsigeo2011_ver2_2.gdc   # 楕円体高変換用ジオイドモデル (*.gdc)
- GRP_OUTPUT =   # 出力
- DestDataset_CESIUM3DTILES = $(FME_MF_DIR_USERTYPED)fn002_output\3d-tiles   # 3D Tiles データセット出力先フォルダー
- DestDataset_MVT_TILESET = $(FME_MF_DIR_USERTYPED)fn002_output\mvt   # MVT データセット出力先フォルダー
- FBX_FOLDER =   # FBX出力先フォルダー (テスト用オプション)

Readers:
- POSTGRES_1: POSTGRES from $(SourceDataset_POSTGRES)
- GEOTIFF_1: GEOTIFF from $(SourceDataset_GEOTIFF)
- XLSXR_1: XLSXR from $(SourceDataset_XLSXR)
- OBJ_2: OBJ from $(SourceDataset_OBJ_3)
- OBJ_1: OBJ from $(SourceDataset_OBJ)

Writers:
- CESIUM3DTILES_1: CESIUM3DTILES to $(DestDataset_CESIUM3DTILES)
- MVT_TILESET_1: MVT_TILESET to $(DestDataset_MVT_TILESET)

AttributeManager_3
    ATTR_TABLE:
      REMOVE _dataset (buffer)
      REMOVE name (buffer)
      REMOVE dimension (buffer)
      REMOVE coordsys (buffer)
    USER_EXPOSED_ATTRIBUTES = _dataset,name,package,facility_code,dimension,coordsys,fme_basename
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(package) NOT_IN veg,area",施設,"BOOL_OP,OR,COMPOSITE_TEST,""""""1"""""",TEST_CLAUSE,TEST @Value(package) = veg",樹木,"BOOL_OP,OR,COMPOSITE_TEST,""""""1"""""",TEST_CLAUSE,TEST @Value(package) = area",区域
    施設 -> FeatureMerger_2 [SUPPLIER]
    樹木 -> FeatureMerger_3 [SUPPLIER]
    区域 -> Junction_9
Note: JSONFlattener : Input
Junction_9
    -> Junction_11
Note: TestFilter : 区域
Junction_11
    -> JSONFlattener
JSONFlattener
    ERROR_LIST_ATTR = _json_error
    JSON_DOCUMENT = @Value(attrib)
    READ_FROM_FILE = NO
    RECURSIVE = Yes
    -> AttributeExposer
AttributeExposer
    ATTR_TABLE = feature_type,buffer,name,buffer,function,buffer,nominalArea,real64,location,buffer,startFrom,buffer
    -> Zone (writer MVT_TILESET_1)
Note: [MVT_TILESET]
Zone (writer MVT_TILESET_1)
    attributes: feature_type string, name string, function string, nominalArea double, location string, startFrom string
Note: 単独木概形モデル / 3_樹種不明/1_広葉樹/2_針葉樹 / [OBJ]
3_樹種不明 (reader OBJ_1)
    -> BoundsExtractor
Note: 変形させない程度に軽量化
Note: Mesh -> MultiSurface / Mesh, CompositeSurface よりも MultiSurface の方が 3D Tile のサイズが小さくなった。
MeshSimplifier
    AMOUNT = 0.6
    MODE = RELATIVE
    SIMPLIFIED -> GeometryPartExtractor
Note: 幹を細くする
Scaler
    RASTER_SCALING = Extents
    SCALE_ORIGIN = 0,0
    TEXT_LOC_ONLY = Location and Size
    XSCALE = 0.25
    YSCALE = 0.25
    ZSCALE = 1
    SCALED -> AttributeManager_4
Junction_2
    -> AttributeManager_4
AttributeManager_4
    ATTR_TABLE:
      RENAME_SET_VALUE _tree_type > facility_name_optional (varchar(200))
      REMOVE _part_number (uint64)
      REMOVE _geometry_name (buffer)
      REMOVE _part (buffer)
      REMOVE _model_width (varchar(200))
    -> Aggregator_2
Aggregator_2
    ACCUM_ATTRS_NAME = Use Attributes From One Feature
    AGGREGATE_TYPE = Homogeneous Collection (If Possible)
    GROUP_BY = facility_name_optional
    MODE = Geometry - Assemble One Level
    SEP = ,
    AGGREGATE -> FeatureMerger_6 [SUPPLIER]
Note: DEM [GEOTIFF]
GEOTIFF (reader GEOTIFF_1)
    -> PointCloudCombiner
Note: 点群に変換
PointCloudCombiner
    ACCUM_ATTRS_NAME = Yes
    EXTRACT_RASTER_NODATA_NAME = No
    SPACING = 1.0
    -> PROJReprojector_2
Note: EPSG:3857 に変換
PROJReprojector_2
    DEST = EPSG:3857
    INTERPOLATION_TYPE_NAME = Nearest Neighbor
    RASTER_CELL_SIZE = Preserve Cells
    RASTER_TOLERANCE = 0.0
    TRANSFORM_TYPE = Automatic Transformation
    REPROJECTED -> CsmapReprojector_2
Note: 楕円体高に変換
CsmapReprojector_2
    DEST = EPSG:3857
    GEOID_HEIGHT_GRID = $(GEOID_HEIGHT_GRID)
    INTERPOLATION_TYPE_NAME = Nearest Neighbor
    RASTER_CELL_SIZE = Preserve Cells
    RASTER_TOLERANCE = 0.0
    VERTICAL_HANDLING = Orthometric height -> Geocentric or ellipsoid height
    REPROJECTED -> SurfaceDraper [POINTS/LINES]
Note: ジオメトリを結合
FeatureMerger_2
    ATTR_ACCUM_MODE = Merge Supplier
    ATTR_CONFLICT_RES = Use Requestor
    IGNORE_NULLS = No
    JOIN_KEYS = @Value(facility_code) @Value(facility_code) AUTO
    MERGE_TYPE = Attributes and Geometry
    PROCESS_DUPS = NO
    REJECT_NULL_MISSING_KEYS = No
    SUPPLIERS_FIRST = No
    MERGED -> AttributeFilter
AttributeFilter
    ATTR_NAME = package
    ATTR_VALUES = trk,bldg,brid,wtr,frn,frn-ext,<Empty>,<Missing>,<Null>,<Unfiltered>
    trk -> trk (writer MVT_TILESET_1)
    bldg -> Junction_6
    brid -> Junction_6
    wtr -> Junction_6
    frn -> Tester_2
    frn-ext -> Junction
Note: [MVT_TILESET]
trk (writer MVT_TILESET_1)
    attributes: facility_code string, facility_name string, specific_facility_name string, facility_type string, installation_year int64, expected_usage_period int64, main_material_optional string, size string, management_type string
Junction_6
    -> AttributeValueMapper_2
Note: 3Dと2Dに分岐
Tester_2
    BOOL_OP = OR
    TEST_CLAUSE = TEST @Dimension() = 3
    TEST_MODE = TEST
    PASSED -> AttributeValueMapper_2
    FAILED -> PROJReprojector
Note: feature_type 設定
AttributeValueMapper_2
    LUT = bldg,Building,brid,Bridge,wtr,WaterBody,frn,CityFurniture
    MAPPING_DIRECTION = FORWARD
    SRC = package
    VAL_ATTR = feature_type
    -> AttributeManager_12
    -> Tester_5
AttributeManager_12
    ATTR_TABLE = REMOVE attrib (buffer)
    -> tileset (writer CESIUM3DTILES_1)
Note: 遊戯施設を選択
Tester_5
    BOOL_OP = OR
    TEST_CLAUSE = TEST @Value(facility_type) = 遊戯施設
    TEST_MODE = TEST
    PASSED -> PROJReprojector_3
AttributeManager_13
    ATTR_TABLE:
      SET_TO package (buffer) = frn-transparent-wrapper
      REMOVE _zmin (real64)
      REMOVE _zmax (real64)
      REMOVE _list{}._zmin (real64)
      REMOVE _list{}._zmax (real64)
      REMOVE _zmin.min (real64)
      REMOVE __unused (real64)
      REMOVE _zmax.max (real64)
      REMOVE attrib (buffer)
    USER_EXPOSED_ATTRIBUTES = facility_code,facility_name,specific_facility_name,facility_type,installation_year,expected_usage_period,main_material_optional,size,management_type,package,_zmin,_zmax,_list{}._zmin,_list{}._zmax,_zmin.min,__unused,_zmax.max
    -> Junction_12
Note: 3D Tiles
Junction_12
    -> Junction_13
Note: 遊戯施設の透明 (A=0.05) カバー / AttributeManager_13 : Output
Junction_13
    -> tileset (writer CESIUM3DTILES_1)
Note: [CESIUM3DTILES]
Note: 遊戯施設の透明カバーソリッド作成
tileset (writer CESIUM3DTILES_1)
    attributes: feature_type string, facility_code string, facility_name string, specific_facility_name string, facility_type string, installation_year int, expected_usage_period int, main_material_optional string, size string, management_type string
Note: frn (都市設備) / 3D : 遊戯施設 / 2D : 柵・門・看板 / frn-ext : 公共測量成果の精度を満たさない柵・門・看板
Junction
    -> PROJReprojector
Note: EPSG:3857に変換
PROJReprojector
    DEST = EPSG:3857
    INTERPOLATION_TYPE_NAME = Nearest Neighbor
    RASTER_CELL_SIZE = Preserve Cells
    RASTER_TOLERANCE = 0.0
    TRANSFORM_TYPE = Automatic Transformation
    REPROJECTED -> Junction_7
Note: 柵・門・看板の3Dモデル作成、出力 / FeatureMerger_4 : Requestor
Junction_7
    -> Junction_8
Note: 都市設備のうち柵・門・看板の3Dオブジェクト作成、3D Tiles変換
Note: PROJReprojector : Reprojected
Junction_8
    -> FeatureMerger_4 [REQUESTOR]
Note: 柵・門にサイズ等を結合
FeatureMerger_4
    ATTR_ACCUM_MODE = Merge Supplier
    ATTR_CONFLICT_RES = Use Requestor
    IGNORE_NULLS = No
    JOIN_KEYS = @Value(facility_code) @Value(施設コード) AUTO
    MERGE_TYPE = Attributes Only
    PROCESS_DUPS = NO
    REJECT_NULL_MISSING_KEYS = No
    SUPPLIERS_FIRST = No
    MERGED -> Tester_3
    UNMERGED_REQUESTOR -> FeatureMerger_5 [REQUESTOR]
Note: 柵と門に分岐
Tester_3
    BOOL_OP = OR
    TEST_CLAUSE = TEST @Value(facility_name) = 柵
    TEST_MODE = TEST
    PASSED -> AttributeCreator
    FAILED -> AttributeCreator_2
Deaggregator_2
    EXPLODE_INSTANCES = No
    LIST_ATTR_MODE_LOOKUP = LEAN
    MODE = Flatten All Levels
    SPLIT_COMPOSITES = No
    DEAGGREGATED -> Counter
Counter
    CNT_ATTR = _feature_index
    SCOPE = Local
    START = 0
    -> LineDivider [Line]
LineDivider
    DIM = 2D
    MODE = ToApproxLength
    OUTPUT = LinesAndPoints
    VALUE = 2
    Line -> SurfaceDraper [DRAPE_FEATURES]
    Point -> SurfaceDraper [DRAPE_FEATURES]
Note: 看板にサイズ等を結合
FeatureMerger_5
    ATTR_ACCUM_MODE = Merge Supplier
    ATTR_CONFLICT_RES = Use Requestor
    IGNORE_NULLS = No
    JOIN_KEYS = @Value(facility_code) @Value(施設コード) AUTO
    MERGE_TYPE = Attributes Only
    PROCESS_DUPS = NO
    REJECT_NULL_MISSING_KEYS = No
    SUPPLIERS_FIRST = No
    MERGED -> AttributeCreator_3
GeometryExtractor
    ATTR = _geometry
    KIND_LONG = FME Binary
    REMOVE_GEOMETRY = No
    -> Counter_2
Counter_2
    CNT_ATTR = _feature_index
    SCOPE = Local
    START = 0
    -> CenterPointReplacer
CenterPointReplacer
    POINTTYPE = CENTER
    POINT -> SurfaceDraper [DRAPE_FEATURES]
Note: DEMに基づいて各頂点に z = 楕円体高を設定
SurfaceDraper
    ADDZ_TYPE = Replace Z
    DRAPE_TYPE = VERTEX
    INTERPOLATION_TYPE = AUTO
    TOLERANCE = 0
    DRAPED_FEATURES -> AttributeFilter_5
AttributeFilter_5
    ATTR_NAME = feature_type
    ATTR_VALUES = Fence,Gate,Signboard,<Empty>,<Missing>,<Null>,<Unfiltered>
    Fence -> GeometryFilter
    Gate -> ElevationExtractor
    Signboard -> ElevationExtractor_2
GeometryFilter
    FILTER_MODE = SIMPLE
    FILTER_MULTI = FILTER_TYPES]"Point Line"]FME_CONTROLLER_QUERY_FILE]]FME_CONTROLLER_CHOICE]Simple
    Point -> CoordinateExtractor
    Curve -> Offsetter_2
PipeReplacer
    OUTER_RADIUS = @Value(厚さ（mm）)*0.001*0.5
    -> PipeEvaluator
PipeEvaluator
    PROFILE_NUM_EDGES = 16
    -> Aggregator_3
Aggregator_3
    ACCUM_ATTRS_NAME = Use Attributes From One Feature
    AGGREGATE_TYPE = Homogeneous Collection (If Possible)
    GROUP_BY = _feature_index
    MODE = Geometry - Assemble One Level
    SEP = ,
    AGGREGATE -> Junction_3
ElevationExtractor
    ELE_ATTR = _z
    -> GeometryReplacer
GeometryReplacer
    KIND_LONG = FME Binary
    REMOVE_ATTRIBUTE = Yes
    SOURCE = @Value(_geometry)
    -> Bufferer
Bufferer
    ANGLE = 22.5
    CAP_STYLE = None
    CORNER_STYLE = Arc
    MODE = AREA
    OFFSET = @Value(厚さ（mm）)*0.0005
    OFFSET_UNITS = NONE
    PRECISION = APPROX
    BUFFERED -> 3DForcer
3DForcer
    KEEPZVAL = No
    ZVALATTR = @Value(_z)
    -> Extruder
Extruder
    DIRECTION = Vertical
    DISTANCE = @Value(高さ（mm）)*0.001
    EXTRUDED -> Junction_3
Junction_3
    -> AttributeManager_11
ElevationExtractor_2
    ELE_ATTR = _z
    -> GeometryReplacer_2
GeometryReplacer_2
    KIND_LONG = FME Binary
    REMOVE_ATTRIBUTE = Yes
    SOURCE = @Value(_geometry)
    -> GeometryRefiner
GeometryRefiner
    -> CoordinateExtractor_2
CoordinateExtractor_2
    LIST_NAME = _indices
    MODE = All Coordinates
    -> Tester_4
Tester_4
    BOOL_OP = OR
    TEST_CLAUSE = TEST _indices{2}.x ATTRIBUTE_IS_MISSING ""
    TEST_MODE = TEST
    PASSED -> CenterPointExtractor
    FAILED -> VertexCreator_2
CenterPointExtractor
    CENTX = _x
    CENTY = _y
    EXTRACTIONMODE = CENTER
    -> 2DVectorCalculator
2DVectorCalculator
    ATTR_EXP = _2dvectorcalculator.+
    BEG_INDEX = 0
    DIRECTION = START_TO_END
    END_INDEX = -1
    LENGTH = 1.0
    REPLACE_GEOM = No
    VX_ATTR = _vx
    VY_ATTR = _vy
    -> AttributeManager_8
AttributeManager_8
    ATTR_TABLE:
      REMOVE 施設コード (varchar(7))
      RENAME_SET_VALUE 形状パターン > _shape_type (varchar(1))
      SET_TO _width (varchar(200)) = @Evaluate(@Length())
      RENAME_SET_VALUE 厚さ（mm） > _thickness (number(3,0)) = @Evaluate(@CurrentAttribute()*0.001)
      RENAME_SET_VALUE 高さ（mm） > _height (number(4,0)) = @Evaluate(@CurrentAttribute()*0.001)
      SET_TO _rotation_angle (varchar(200)) = @Evaluate(@radToDeg(@atan2(@Value(_vy),@Value(_vx))))
      REMOVE _indices{}.x (real64)
      REMOVE _indices{}.y (real64)
      REMOVE _indices{}.z (real64)
      REMOVE _vx (buffer)
      REMOVE _vy (buffer)
    -> FeatureMerger_7 [REQUESTOR]
Note: DB(CityGML)でジオメトリが与えられているものとその他に分岐
FeatureMerger_3
    JOIN_KEYS = @Value(facility_code) @Value(facility_code) AUTO
    MERGE_TYPE = Geometry
    PROCESS_DUPS = NO
    REJECT_NULL_MISSING_KEYS = No
    SUPPLIERS_FIRST = No
    MERGED -> Junction_4
    UNMERGED_REQUESTOR -> AttributeManager_6
Note: 樹木 (単独木) のジオメトリ / DBにジオメトリが格納されている単独木 (i.e. CityGML LOD3モデル) についてはそれを使用、その他については別途作成した概形モデル (OBJ) のサイズ、位置を合わせて使用する。
Junction_4
    -> Junction_5
Junction_5
    -> AttributeManager_7
AttributeManager_6
    ATTR_TABLE:
      SET_TO _x (real64) = @Value(longitude)
      SET_TO _y (real64) = @Value(latitude)
      SET_TO _z (real64) = @Value(elevation)
    -> CsmapAttributeReprojector
CsmapAttributeReprojector
    DEST = EPSG:3857
    GEOID_HEIGHT_GRID = $(GEOID_HEIGHT_GRID)
    SOURCE = EPSG:4326
    VERTICAL_HANDLING = Orthometric height -> Geocentric or ellipsoid height
    XATTR = _x
    YATTR = _y
    ZATTR = _z
    REPROJECTED -> FeatureMerger_6 [REQUESTOR]
FeatureMerger_6
    ATTR_ACCUM_MODE = Merge Supplier
    ATTR_CONFLICT_RES = Use Requestor
    IGNORE_NULLS = No
    JOIN_KEYS = @Value(facility_name_optional) @Value(facility_name_optional) AUTO
    MERGE_TYPE = Attributes and Geometry
    PROCESS_DUPS = NO
    REJECT_NULL_MISSING_KEYS = No
    SUPPLIERS_FIRST = No
    MERGED -> ExpressionEvaluator
ExpressionEvaluator
    ACTION = Create New Attribute
    EXPRESSION = @Value(height)/@Value(_model_height)
    VAL_ATTR = _scale
    -> Scaler_2
Scaler_2
    RASTER_SCALING = Extents
    SCALE_ORIGIN = 0,0
    TEXT_LOC_ONLY = Location and Size
    XSCALE = @Value(_scale)
    YSCALE = @Value(_scale)
    ZSCALE = @Value(_scale)
    SCALED -> Offsetter
Offsetter
    MODE = Cartesian Coordinate
    XOFF = @Value(_x)
    YOFF = @Value(_y)
    ZOFF = @Value(_z)
    OFFSET -> CoordinateSystemSetter_2
CoordinateSystemSetter_2
    COORDSYS = EPSG:3857
    -> AttributeManager_7
AttributeManager_7
    ATTR_TABLE:
      REMOVE _x (real64)
      REMOVE _y (real64)
      REMOVE _z (real64)
      REMOVE _model_height (varchar(200))
      REMOVE _scale (real64)
    -> solitary-tree (writer CESIUM3DTILES_1)
Note: [CESIUM3DTILES]
solitary-tree (writer CESIUM3DTILES_1)
    attributes: facility_code string, facility_name_optional string, specific_facility_name string, perimeter float, height float, quantity_numeric float, quantity_unit string, latitude float, longitude float, elevation float
Note: 概形モデル (kanbanA, B, C, D, E) / [OBJ]
kanbanA (reader OBJ_2)
    -> BoundsExtractor_2
BoundsExtractor_2
    XMAX = _xmax
    XMIN = _xmin
    YMAX = _ymax
    YMIN = _ymin
    ZMAX = _zmax
    ZMIN = _zmin
    -> AttributeManager_9
AttributeManager_9
    ATTR_TABLE:
      SET_TO _shape_type (varchar(200)) = @LowerCase(@Right(@Value(fme_feature_type),1))
      SET_TO _model_width (varchar(200)) = @Evaluate(@Value(_xmax)-@Value(_xmin))
      SET_TO _model_thickness (varchar(200)) = @Evaluate(@Value(_ymax)-@Value(_ymin))
      SET_TO _model_height (varchar(200)) = @Evaluate(@Value(_zmax)-@Value(_zmin))
      REMOVE fme_feature_type (buffer)
      REMOVE _xmin (real64)
      REMOVE _xmax (real64)
      REMOVE _ymin (real64)
      REMOVE _ymax (real64)
      REMOVE _zmin (real64)
      REMOVE _zmax (real64)
    -> FeatureMerger_7 [SUPPLIER]
AttributeManager_11
    ATTR_TABLE:
      REMOVE package (buffer)
      REMOVE _feature_index (int64)
      REMOVE _shape_type (varchar(1))
      REMOVE _width (varchar(200))
      REMOVE _thickness (number(3,0))
      REMOVE _height (number(4,0))
      REMOVE _rotation_angle (varchar(200))
      REMOVE _x (real64)
      REMOVE _y (real64)
      REMOVE _z (real64)
      REMOVE _model_width (varchar(200))
      REMOVE _model_thickness (varchar(200))
      REMOVE _model_height (varchar(200))
      REMOVE 施設コード (varchar(7))
      REMOVE 高さ（mm） (number(4,0))
      REMOVE 厚さ（mm） (number(3,0))
      REMOVE 形状パターン (varchar(1))
      REMOVE _geometry (buffer)
      REMOVE attrib (buffer)
    -> fence-gate-signboard (writer CESIUM3DTILES_1)
Note: [CESIUM3DTILES]
fence-gate-signboard (writer CESIUM3DTILES_1)
    attributes: feature_type string, facility_code string, facility_type string, facility_name string, specific_facility_name string, size string, main_material_optional string, installation_year int, expected_usage_period int, management_type string

Bookmark: DBに格納した公園施設, 樹木（単独木）, 区域のジオメトリのリストア
echigo_facility_geometry (reader POSTGRES_1)
    attributes: package varchar, facility_code varchar, dimension int2, coordsys varchar, fbx_binary bytea, attrib json
    -> Sorter
Sorter
    SORT_PARM = package ALPHA ASCENDING
    SORTED -> FeatureMerger [REQUESTOR]
Creator
    GEOMTYPE = Geometry Object
    NUM = 1
    CREATED -> TempPathnameCreator
TempPathnameCreator
    PATHNAME_ATTR = _temp_dir
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeManager
AttributeManager
    ATTR_TABLE:
      RENAME_SET_VALUE fbx_binary > data_file_data (binarybuffer)
      SET_TO _temp_dir (buffer) = FME_CONDITIONAL:DEFAULT_VALUE'_FME_NO_OP_'BOOL_OP;OR;COMPOSITE_TEST;1;TEST $(FBX_FOLDER) != _FME_BLANK_STRING_'$(FBX_FOLDER)'FME_NUM_CONDITIONS2___
    -> FeatureWriter [public.echigo_facility_geometry]
FeatureWriter
    DATAFILE_COORDINATE_SYSTEM_GRANULARITY = FEATURE
    DATAFILE_DESTINATION_DATASETTYPE_VALIDATION = Yes
    DATAFILE_ENCODING = fme-binary
    DATAFILE_END_OF_LINE = System
    DATAFILE_MIME_TYPE = text/plain
    DATAFILE_OVERWRITE_FILE = YES
    DATAFILE_WRITE_LAST_EOL = YES
    DATAFILE_WRITE_UTF8_BOM = YES
    DATASET = @Value(_temp_dir)/@Value(package)
    DATASET_ATTR = _dataset
    FEATURE_TYPE_LIST_ATTR = _feature_types
    FORMAT = DATAFILE
    GROUP_BY = package
    MORE_SUMMARY_ATTRS = coordsys dimension facility_code package attrib
    TOTAL_FEATURES_WRITTEN_ATTR = _total_features_written
    SUMMARY -> ListExploder
ListExploder
    ATTR_ACCUM_MODE = Merge List Attributes
    ATTR_CONFLICT_RES = Use List Attribute Values
    LIST_ATTR = _feature_types{}
    ELEMENTS -> AttributeManager_2
AttributeManager_2
    ATTR_TABLE:
      REMOVE count (uint64)
      REMOVE _total_features_written (uint64)
    -> FeatureReader [INITIATOR]
FeatureReader
    ATTRIBUTES = bldg_BEN0001,
    ATTR_ACCUM_MODE = Merge Initiator and Result
    ATTR_CONFLICT_RES = Use Result
    ATTR_IGNORE_NULLS = No
    COMBINE_GEOM = Use Result
    DATASET = @Value(_dataset)/@Value(name)
    FBX_CONVERT_TO_METERS = No
    FBX_MOVE_TO_WORLD_COORDSYS = Yes
    FORMAT = FBX
    INTERACT = NONE
    ORDER_RESULTS = No
    OUTPUT_FEATURES_DISPLAY = Schema and Data Features
    <OTHER> -> CoordinateSystemSetter

Bookmark: 座標系設定および3Dジオメトリの z を楕円体高に変換
CoordinateSystemSetter
    COORDSYS = @Value(coordsys)
    -> Tester
Tester
    BOOL_OP = OR
    TEST_CLAUSE = TEST @Value(dimension) = 3
    TEST_MODE = TEST
    PASSED -> CsmapReprojector
    FAILED -> 2DForcer
CsmapReprojector
    DEST = @Value(coordsys)
    GEOID_HEIGHT_GRID = $(GEOID_HEIGHT_GRID)
    INTERPOLATION_TYPE_NAME = Nearest Neighbor
    RASTER_CELL_SIZE = Preserve Cells
    RASTER_TOLERANCE = 0.0
    SOURCE = @Value(coordsys)
    VERTICAL_HANDLING = Orthometric height -> Geocentric or ellipsoid height
    REPROJECTED -> AttributeManager_3
2DForcer
    2D -> AttributeManager_3

Bookmark: モデルのサイズとタイプ識別子 (q, b, c) 抽出
BoundsExtractor
    XMAX = _xmax
    XMIN = _xmin
    ZMAX = _zmax
    ZMIN = _zmin
    -> AttributeManager_5
AttributeManager_5
    ATTR_TABLE:
      SET_TO _model_width (varchar(200)) = @Evaluate(@Value(_xmax)-@Value(_xmin))
      SET_TO _model_height (varchar(200)) = @Evaluate(@Value(_zmax)-@Value(_zmin))
      SET_TO _tree_type (varchar(200)) = @Substring(@Value(fme_feature_type),2)
      REMOVE fme_feature_type (buffer)
      REMOVE _xmin (real64)
      REMOVE _xmax (real64)
      REMOVE _zmin (real64)
      REMOVE _zmax (real64)
    -> Deaggregator

Bookmark: 樹冠と幹に分割
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeValueMapper
AttributeValueMapper
    LUT = 0,樹冠,1,幹
    MAPPING_DIRECTION = FORWARD
    SRC = _part_number
    VAL_ATTR = _part
    -> MeshSimplifier

Bookmark: Mesh -> MultiSurface
GeometryPartExtractor
    GQUERY:
      for $geom in //geometry
      where $geom/@fme_geometry_type = 'Mesh Part'
      return number($geom/@fme_id)
    EXTRACTED -> Aggregator
Aggregator
    ACCUM_ATTRS_NAME = Use Attributes From One Feature
    AGGREGATE_TYPE = Homogeneous Collection (If Possible)
    GROUP_BY = _part _tree_type
    MODE = Geometry - Assemble One Level
    SEP = ,
    AGGREGATE -> AttributeFilter_2

Bookmark: 樹冠と幹にそれぞれカラーアピアランスを設定
AttributeFilter_2
    ATTR_NAME = _part
    ATTR_VALUES = 幹,樹冠,<Empty>,<Missing>,<Null>,<Unfiltered>
    幹 -> AttributeFilter_3
    樹冠 -> AttributeFilter_4
AttributeFilter_3
    ATTR_NAME = _tree_type
    ATTR_VALUES = 広葉樹,<Unfiltered>,<Empty>,<Missing>,<Null>
    広葉樹 -> GeometryColorSetter
    <UNFILTERED> -> GeometryColorSetter_2
GeometryColorSetter
    ALPHA = 1
    FILL_COLOR = 0.545098,0.270588,0.0745098
    MODE = Fixed
    REC = Yes
    SIDE = Both
    COLORED -> Scaler
GeometryColorSetter_2
    ALPHA = 1
    FILL_COLOR = 0.368627,0.14902,0.0705882
    MODE = Fixed
    REC = Yes
    SIDE = Both
    COLORED -> Scaler
Note: a) 樹形が丸のもの：樹冠 #4CAF50（明るめの緑）、幹 #8B4513（茶色） / b) それ以外の樹木：樹冠 #006400（濃い緑）、幹 #5E2612（濃い茶色）
AttributeFilter_4
    ATTR_NAME = _tree_type
    ATTR_VALUES = 広葉樹,<Unfiltered>,<Empty>,<Missing>,<Null>
    広葉樹 -> GeometryColorSetter_3
    <UNFILTERED> -> GeometryColorSetter_4
GeometryColorSetter_3
    ALPHA = 1
    FILL_COLOR = 0.298039,0.686275,0.313725
    MODE = Fixed
    REC = Yes
    SIDE = Both
    COLORED -> Junction_2
GeometryColorSetter_4
    ALPHA = 1
    FILL_COLOR = 0,0.392157,0
    MODE = Fixed
    REC = Yes
    SIDE = Both
    COLORED -> Junction_2

Bookmark: 概形3Dモデル調整パラメーター (Excel)
柵・門 (reader XLSXR_1)
    attributes: 施設コード char(7), 高さ（mm） number(4,0), 厚さ（mm） number(3,0)
    -> FeatureMerger_4 [SUPPLIER]
看板 (reader XLSXR_1)
    attributes: 施設コード char(7), 形状パターン char(1), 高さ（mm） number(4,0), 厚さ（mm） number(2,0)
    -> FeatureMerger_5 [SUPPLIER]

Bookmark: PostgreSQL 公園管理DBテーブル
echigo_facility_table (reader POSTGRES_1)
    attributes: park_code text, park_name text, park_type text, facility_code text,PrimaryKey, previous_facility_code text, facility_type text, facility_name text, facility_name_optional text, specific_facility_name text, quantity_numeric int4, quantity_unit text, size text, main_material text, main_material_optional text, installation_year int4, elapsed_years int4, disposal_limit_period int4, expected_usage_period int4, repairs_before_healthcheck_exists int2, repairs_before_healthcheck_year int4, health_check_year int4, health_check_deterioration_status text, health_check_condition text, health_check_urgency text, management_type text, updated_year_with_measures int4, cost_2020_thousand_yen int4, content_2020 text, cost_2021_thousand_yen int4, content_2021 text,
      cost_2022_thousand_yen int4, content_2022 text, cost_2023_thousand_yen int4, content_2023 text, cost_2024_thousand_yen int4, content_2024 text, cost_2025_thousand_yen int4, content_2025 text, cost_2026_thousand_yen int4, content_2026 text, cost_2027_thousand_yen int4, content_2027 text, cost_2028_thousand_yen int4, content_2028 text, cost_2029_thousand_yen int4, content_2029 text, note_for_longevity text, color text
    -> AttributeManager_facility
echigo_tree_table (reader POSTGRES_1)
    attributes: park_code text, park_name text, park_type text, facility_code text, facility_type text, facility_name text, facility_name_optional text, specific_facility_name text, perimeter float8, height float8, quantity_numeric float8, quantity_unit text, note text, latitude float8, longitude float8, elevation float8
    -> AttributeManager_tree

Bookmark: 可視化に不要な属性を削除
AttributeManager_facility
    ATTR_TABLE:
      REMOVE park_code (buffer)
      REMOVE park_name (buffer)
      REMOVE park_type (buffer)
      REMOVE previous_facility_code (buffer)
      REMOVE facility_name_optional (buffer)
      REMOVE quantity_numeric (int32)
      REMOVE quantity_unit (buffer)
      REMOVE main_material (buffer)
      REMOVE elapsed_years (int32)
      REMOVE disposal_limit_period (int32)
      REMOVE repairs_before_healthcheck_exists (int16)
      REMOVE repairs_before_healthcheck_year (int32)
      REMOVE health_check_year (int32)
      REMOVE health_check_deterioration_status (buffer)
      REMOVE health_check_condition (buffer)
      REMOVE health_check_urgency (buffer)
      REMOVE updated_year_with_measures (int32)
      REMOVE cost_2020_thousand_yen (int32)
      REMOVE content_2020 (buffer)
      REMOVE cost_2021_thousand_yen (int32)
      REMOVE content_2021 (buffer)
      REMOVE cost_2022_thousand_yen (int32)
      REMOVE content_2022 (buffer)
      REMOVE cost_2023_thousand_yen (int32)
      REMOVE content_2023 (buffer)
      REMOVE cost_2024_thousand_yen (int32)
      REMOVE content_2024 (buffer)
      REMOVE cost_2025_thousand_yen (int32)
      REMOVE content_2025 (buffer)
      REMOVE cost_2026_thousand_yen (int32)
      REMOVE content_2026 (buffer)
      REMOVE cost_2027_thousand_yen (int32)
      REMOVE content_2027 (buffer)
      REMOVE cost_2028_thousand_yen (int32)
      REMOVE content_2028 (buffer)
      REMOVE cost_2029_thousand_yen (int32)
      REMOVE content_2029 (buffer)
      REMOVE note_for_longevity (buffer)
      REMOVE color (buffer)
    -> FeatureMerger_2 [REQUESTOR]
AttributeManager_tree
    ATTR_TABLE:
      REMOVE park_code (buffer)
      REMOVE park_name (buffer)
      REMOVE park_type (buffer)
      REMOVE facility_type (buffer)
      REMOVE facility_name (buffer)
      REMOVE note (buffer)
    -> FeatureMerger_3 [REQUESTOR]

Bookmark: 遊戯施設の透明カバーソリッド作成
PROJReprojector_3
    DEST = EPSG:3857
    INTERPOLATION_TYPE_NAME = Nearest Neighbor
    RASTER_CELL_SIZE = Preserve Cells
    RASTER_TOLERANCE = 0.0
    TRANSFORM_TYPE = Automatic Transformation
    REPROJECTED -> Sorter_2
Sorter_2
    SORT_PARM = facility_code ALPHA ASCENDING
    SORTED -> BoundsExtractor_3
BoundsExtractor_3
    ZMAX = _zmax
    ZMIN = _zmin
    -> 2DForcer_2
2DForcer_2
    2D -> Bufferer_2
Bufferer_2
    ANGLE = 22.5
    CAP_STYLE = Arc
    CORNER_STYLE = Arc
    GROUP_BY = facility_code
    LIST_ATTRS_TO_INCLUDE = _zmax _zmin
    LIST_NAME = _list
    MODE = AREA
    OFFSET = 2
    OFFSET_UNITS = NONE
    PRECISION = APPROX
    BUFFERED -> Bufferer_3
Bufferer_3
    ANGLE = 22.5
    CAP_STYLE = Arc
    CORNER_STYLE = Arc
    MODE = AREA
    OFFSET = -1.7
    OFFSET_UNITS = NONE
    PRECISION = APPROX
    BUFFERED -> ListRangeExtractor
ListRangeExtractor
    MAX = __unused
    MIN = _zmin.min
    SRC_LIST = _list{}._zmin
    -> ListRangeExtractor_2
ListRangeExtractor_2
    MAX = _zmax.max
    MIN = __unused
    SRC_LIST = _list{}._zmax
    -> DonutHoleExtractor
DonutHoleExtractor
    DEAGGREGATE_INPUT = Yes
    OUTERSHELL -> Generalizer
    <REJECTED> -> Junction_10
Generalizer
    ALG_TEXT = Thin (Generalize)
    TOLERANCE = 0.1
    -> 3DForcer_2
3DForcer_2
    KEEPZVAL = No
    ZVALATTR = @Value(_zmin.min)
    -> Extruder_2
Extruder_2
    DIRECTION = Vertical
    DISTANCE = @Value(_zmax.max)-@Value(_zmin.min)
    EXTRUDED -> Aggregator_4
Aggregator_4
    ACCUM_ATTRS_NAME = Use Attributes From One Feature
    AGGREGATE_TYPE = Homogeneous Collection (If Possible)
    GROUP_BY = facility_code
    MODE = Geometry - Assemble One Level
    SEP = ,
    AGGREGATE -> GeometryColorSetter_5
GeometryColorSetter_5
    ALPHA = 0.05
    FILL_COLOR = 1,1,1
    MODE = Fixed
    REC = Yes
    SIDE = Both
    COLORED -> AttributeManager_13
Junction_10

Bookmark: feature_type 設定
AttributeCreator
    ATTR_TABLE = SET_TO feature_type (buffer) = Fence
    -> Deaggregator_2
AttributeCreator_2
    ATTR_TABLE = SET_TO feature_type (buffer) = Gate
    -> GeometryExtractor
AttributeCreator_3
    ATTR_TABLE = SET_TO feature_type (buffer) = Signboard
    -> GeometryExtractor

Bookmark: 支柱 (鉛直の線分)
CoordinateExtractor
    IND = 0
    MODE = Specify Coordinate
    X_ATTR = _x
    Y_ATTR = _y
    Z_ATTR = _z
    -> VertexCreator
VertexCreator
    CLOSE_LINES = Yes
    IGNORE_DUPLICATES = No
    MEASURE_TYPE = Continuous
    MISSING_VAL_MODE = Compute
    MODE_NAME = Add Point
    XVAL = @Value(_x)
    YVAL = @Value(_y)
    ZVAL = @Value(_z)+@Value(高さ（mm）)*0.001
    -> PipeReplacer

Bookmark: 柵の線形 (3Dライン)
Offsetter_2
    MODE = Cartesian Coordinate
    XOFF = 0
    YOFF = 0
    ZOFF = @Value(高さ（mm）)*0.001
    OFFSET -> LineCombiner_2
LineCombiner_2
    ACCUM_ATTRS_NAME = Use Attributes From One Feature
    BREAK = no
    BREAK_CONNECTION_ATTRIBUTES = facility_code
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> PipeReplacer

Bookmark: V次のラインを中央の頂点を始点とする2線分に変換
VertexCreator_2
    MEASURE_TYPE = Continuous
    MODE_NAME = Replace with Point
    XVAL = @Value(_indices{1}.x)
    YVAL = @Value(_indices{1}.y)
    -> VertexCreator_3
    -> VertexCreator_4
VertexCreator_3
    CLOSE_LINES = Yes
    IGNORE_DUPLICATES = No
    MEASURE_TYPE = Continuous
    MISSING_VAL_MODE = Compute
    MODE_NAME = Add Point
    XVAL = @Value(_indices{0}.x)
    YVAL = @Value(_indices{0}.y)
    -> CenterPointExtractor
VertexCreator_4
    CLOSE_LINES = Yes
    IGNORE_DUPLICATES = No
    MEASURE_TYPE = Continuous
    MISSING_VAL_MODE = Compute
    MODE_NAME = Add Point
    XVAL = @Value(_indices{2}.x)
    YVAL = @Value(_indices{2}.y)
    -> CenterPointExtractor

Bookmark: モデルジオメトリ結合、スケール,回転,位置合わせ
FeatureMerger_7
    ATTR_ACCUM_MODE = Merge Supplier
    ATTR_CONFLICT_RES = Use Requestor
    IGNORE_NULLS = No
    JOIN_KEYS = @Value(_shape_type) @Value(_shape_type) AUTO
    MERGE_TYPE = Attributes and Geometry
    PROCESS_DUPS = NO
    REJECT_NULL_MISSING_KEYS = No
    SUPPLIERS_FIRST = No
    MERGED -> Scaler_3
Scaler_3
    RASTER_SCALING = Extents
    SCALE_ORIGIN = 0,0
    TEXT_LOC_ONLY = Location and Size
    XSCALE = @Value(_width)/@Value(_model_width)
    YSCALE = @Value(_thickness)/@Value(_model_thickness)
    ZSCALE = @Value(_height)/@Value(_model_height)
    SCALED -> 3DRotator
3DRotator
    ANGLE = @Value(_rotation_angle)
    AXIS_CHOICE = Z Axis
    ROTATED -> Offsetter_3
Offsetter_3
    MODE = Cartesian Coordinate
    XOFF = @Value(_x)
    YOFF = @Value(_y)
    ZOFF = @Value(_z)
    OFFSET -> CoordinateSystemSetter_3
CoordinateSystemSetter_3
    COORDSYS = EPSG:3857
    -> AttributeManager_11

FME custom transformer 2DVectorCalculator
Calculates (x, y) components of a 2D vector defined by the parameter settings, and stores them as new attributes.
Optionally this transformer replaces feature geometry with a line segment representing the resulting vector.
Since it can also calculate a normal vector, may be useful to create a perpendicular line against the original geometry.
If there is one of the following conditions, the input feature will be output from the Failed port.
The reason for the failure will be stored in a new attribute named "_faiulre_reason".
- the number of coordinates is less than 2.
- specified start or end index is out of range.
- specified start index is equal to end index.
- the start and end coordinates are too close (the distance is less than 1.0e-8).
Parameters
Start Index:
Specify the index of a coordinate which should be used as start point for defining the vector.
End Index:
Specify the index of a coordinate which should be used as end point for defining the vector.
Note: The Start/End Index should be 0-based sequential number in the sequence of input geometry coordinates.
A negative index can also be used; it indicates the number that was counted from tail of the sequence.
For example, -1 indicates the last one in the sequence; -2 indicates the previous one; and so on.
Vector Direction:
Choose one of these as the direction of the vector.
-----
Start to End
Normal Left
Normal Right
End to Start
-----
Note: "Normal Left/Right" means the left/right hand side perpendicular direction against "Start to End" direction.
Vector Length:
Specify the length of the vector.
Note: If you specify a negative value to this parameter, the resulting vector direction will be reversed against the direction specified by the "Vector Direction" parameter.
X Component Attribute:
Specify the name of attribute that should store x-component of the vector.
Y Component Attribute:
Specify the name of attribute that should store y-component of the vector.
Replace Geometry:
If you choose "No" for this parameter, the original geometry will be preserved with no transformation.
If you choose "Yes", the geometry will be replaced with a line segment.
The direction and length of the line represent the resulting vector, and the start node will be located at a point specified by the "Start Index" parameter.

Parameters:
- BEG_INDEX = 0   # Start Index
- END_INDEX = -1   # End Index
- DIRECTION = START_TO_END   # Start to End,START_TO_END%Normal Left,NORMAL_LEFT%Normal Right,NORMAL_RIGHT%End to Start,END_TO_START Vector Direction
- LENGTH = 1.0   # Vector Length
- VX_ATTR = _vx   # TYPE:varchar(200) X Component Attribute
- VY_ATTR = _vy   # TYPE:varchar(200) Y Component Attribute
- REPLACE_GEOM = No   # Replace Geometry
- ATTR_EXP = _2dvectorcalculator.+   # Expression to Remove

Input (input)
    -> AttributeCreator
Note: AttributeCreator [AttributeCreator] / _2dvectorcalculator.beg_index = @Evaluate($(BEG_INDEX)) / _2dvectorcalculator.end_index = @Evaluate($(END_INDEX)) / _2dvectorcalculator.direction = $(DIRECTION) / _2dvectorcalculator.length = @Evaluate($(LENGTH)) / _2dvectorcalculator.replace_geom = $(REPLACE_GEOM)
AttributeCreator
    ATTR_LIST = _2dvectorcalculator.beg_index,@Evaluate($(BEG_INDEX)),_2dvectorcalculator.end_index,@Evaluate($(END_INDEX)),_2dvectorcalculator.direction,$(DIRECTION),_2dvectorcalculator.length,@Evaluate($(LENGTH)),_2dvectorcalculator.replace_geom,$(REPLACE_GEOM)
    -> TclCaller
TclCaller
    NEW_ATTRIBUTES = _2dvectorcalculator.vx _2dvectorcalculator.vy
    SRC:
      proc calc2DVector {} {
          set numCoords [FME_Coordinates numCoords]
          if {$numCoords < 2} {
              return "the number of coordinates is less than 2"
          }
          set beg [FME_GetAttribute "_2dvectorcalculator.beg_index"]
          if {$beg < 0} {
              set beg [expr $numCoords + $beg]
          }
          if {$beg < 0 || $numCoords <= $beg} {
              return "start index is out of range"
          }
          set end [FME_GetAttribute "_2dvectorcalculator.end_index"]
          if {$end < 0} {
              set end [expr $numCoords + $end]
          }
          if {$end < 0 || $numCoords <= $end} {
              return "end index is out of range"
          }
          if {$beg == $end} {
              return "start index is equal to end index"
          }
          set x0 [FME_Execute Coordinate x $beg FLATTEN_AGGREGATE]
          set y0 [FME_Execute Coordinate y $beg FLATTEN_AGGREGATE]
          set dx [expr [FME_Execute Coordinate x $end FLATTEN_AGGREGATE] - $x0]
          set dy [expr [FME_Execute Coordinate y $end FLATTEN_AGGREGATE] - $y0]
          set len [expr hypot($dx, $dy)]
          if {$len < 1.0e-8} {
              return "start and end coordinates are too close"
          }
          set scale [expr double([FME_GetAttribute "_2dvectorcalculator.length"]) / $len]
          set direction [FME_GetAttribute "_2dvectorcalculator.direction"]
          if {[string equal $direction START_TO_END]} {
              set vx [expr $dx * $scale]
              set vy [expr $dy * $scale]
          } elseif {[string equal $direction NORMAL_LEFT]} {
              set vx [expr -($dy) * $scale]
              set vy [expr $dx * $scale]
          } elseif {[string equal $direction NORMAL_RIGHT]} {
              set vx [expr $dy * $scale]
              set vy [expr -($dx) * $scale]
          } elseif {[string equal $direction END_TO_START]} {
              set vx [expr -($dx) * $scale]
              set vy [expr -($dy) * $scale]
          } else {
              return "Debug: Invalid Direction"
          }
          FME_SetAttribute "_2dvectorcalculator.vx" $vx
          FME_SetAttribute "_2dvectorcalculator.vy" $vy
          if {[string equal [FME_GetAttribute "_2dvectorcalculator.replace_geom"] Yes]} {
              if {[FME_Execute Dimension] == 3} {
                  set z0 [FME_Execute Coordinate z $beg FLATTEN_AGGREGATE]
                  FME_Execute RemoveGeometry
                  FME_Coordinates addCoord $x0 $y0 $z0
                  FME_Coordinates addCoord [expr $x0 + $vx] [expr $y0 + $vy] $z0
              } else {
                  FME_Execute RemoveGeometry
                  FME_Coordinates addCoord $x0 $y0
                  FME_Coordinates addCoord [expr $x0 + $vx] [expr $y0 + $vy]
              }
          }
          return 1
      }
    TCLPROG = calc2DVector
    VAL_ATTR = _2dvectorcalculator.result
    -> Tester
Tester
    BOOL_OP = OR
    TEST_CLAUSE = TEST @Value(_2dvectorcalculator.result) = 1
    TEST_MODE = Automatic
    PASSED -> BulkAttributeRenamer
    FAILED -> BulkAttributeRenamer_3
BulkAttributeRenamer
    ATTRCHOICE = Selected Attributes
    ATTRLIST = _2dvectorcalculator.vx
    PATTERN_ACTION_DISP = Regular Expression Replace
    REPLACE_PATTERN = .+
    REPLACE_STR = $(VX_ATTR)
    -> BulkAttributeRenamer_2
BulkAttributeRenamer_2
    ATTRCHOICE = Selected Attributes
    ATTRLIST = _2dvectorcalculator.vy
    PATTERN_ACTION_DISP = Regular Expression Replace
    REPLACE_PATTERN = .+
    REPLACE_STR = $(VY_ATTR)
    -> BulkAttributeRemover
BulkAttributeRemover
    ATTR_EXP = $(ATTR_EXP)
    -> Output (output)
Output (output)
BulkAttributeRenamer_3
    ATTRCHOICE = Selected Attributes
    ATTRLIST = _2dvectorcalculator.result
    PATTERN_ACTION_DISP = Regular Expression Replace
    REPLACE_PATTERN = .+
    REPLACE_STR = _failure_reason
    -> BulkAttributeRemover_2
BulkAttributeRemover_2
    ATTR_EXP = $(ATTR_EXP)
    -> Failed (output)
Failed (output)

FME custom transformer LineDivider
Divides a line into multiple lines. Resulting lines and/or points which separate the lines will be output.
Every output feature will hold all the attributes of the original feature.
This transformer accepts non-aggregate Curve (Line, Arc or Path) features only.
If an input feature has other type geometry or does not have geometry, it will be output from the <Rejected> port.
Similar functions have been provided by the IterativeSnipper_2013 and the DistanceMarker_2013 in the FME Hub.
Major differences from them are:
1) Integrated their functions so that divided lines and distance markers can be created efficiently at the same time, but users still can also use each function separately. See the "Output" parameter.
2) Added "Measurement Mode" parameter so that users can choose 2D or 3D for measuring lengths.
3) Implemented with a Python script to improve performance, although the algorithm is basically same as theirs.
Parameters
Measurement Mode:
By default, the transformer measures lengths in 2D, but you can change it to 3D with this parameter setting.
Dividing Mode:
Choose one of these modes.
"Shorten to Following Length"
- snips iteratively each input line from its head by the length specified to the "Line Length or Number of Lines" parameter. Length of the final line could be less than the specified length.
"Shorten to Approximately Following Length"
- divides each input line into multiple lines having identical length which is approximately equal to the length specified to the "Line Length or Number of Lines" parameter.
"Divide to Following Number of Lines"
- divides each input line into multiple lines having identical length by the number specified to the "Line Length or Number of Lines" parameter.
Line Length or Number of Lines:
Specify a numeric value if you set "Shorten to Following Length" or "Shorten to Approximately Following Length" in the "Dividing Mode" parameter.
Specify an integer number if you set "Divide to Following Number of Lines" in the "Dividing Mode" parameter.
In both cases, the value must be greater than 0.
Output:
You can control what kind of features should be output with this parameter setting.
By default, the transformer outputs both Lines and Points, but you could run it more efficiently by selecting a preferable option if you need either only Lines or Points.
"Lines"
- outputs divided lines only. Nothing is output from the Point port.
"Lines and Points" (default)
- outputs both divided lines and points which separate the lines; including start and end nodes of the original line.
"Lines and Points except Start and End Nodes"
- outputs both divided lines and points which separate the lines; excluding start and end nodes of the original line.
"Points"
- outputs points only; including start and end nodes of the original line. Nothing is output from the Line port.
"Points except Start and End Nodes"
- outputs points only; excluding start and end nodes of the original line. Nothing is output from the Line port.

Parameters:
- DIM = 2D   # Measurement Mode
- MODE = ToLength
- VALUE =   # Line Length or Number of Lines
- OUTPUT = LinesAndPoints

Line (input)
    -> AggregateFilter
AggregateFilter
    AGGREGATE -> <Rejected> (output)
    NOT_AGGREGATE -> GeometryFilter
GeometryFilter
    BREAK_AGG = No
    GEOM_PORT_NAMES = Line Arc
    LINE -> AttributeCreator
    ARC -> AttributeCreator
    <UNFILTERED> -> <Rejected> (output)
AttributeCreator
    ATTR_LIST = __linedivider.dim,$(DIM),__linedivider.mode,$(MODE),__linedivider.value,@Evaluate($(VALUE)),__linedivider.output,$(OUTPUT)
    -> PythonCaller
PythonCaller
    HIDE_ATTRIBUTES = __linedivider.dim __linedivider.mode __linedivider.value __linedivider.output
    PYTHONSOURCE:
      # 2014-11-15, Takashi Iijima, Original Implementation
      # 2015-05-11, Takashi Iijima, Added Arc support; Fixed a problem on creating interval points of Path
      # 2017-06-26, Takashi Iijima, Updated to improve robustness.
      # 2020-01-12, Takashi Iijima, Changed Default Python Interpreter to 3.6+, saved with FME 2017.1.2.1

      import fmeobjects, math

      class LineDivider(object):
          def input(self, feature):
              is3D = (feature.getAttribute('__linedivider.dim') == '3D')
              mode = feature.getAttribute('__linedivider.mode')
              value = float(feature.getAttribute('__linedivider.value'))
              output = feature.getAttribute('__linedivider.output')
              for attr in ['dim', 'mode', 'value', 'output']:
                  feature.removeAttribute('__linedivider.' + attr)

              coordSys = feature.getCoordSys()
              outputLines = output.startswith('Lines')
              outputPoints = output.startswith('LinesAndPoints') or output.startswith('Points')
              outputEndNodes = outputPoints and not output.endswith('ExceptEndNodes')

              # Get original curve geometry
              curve = feature.getGeometry()
              length = curve.getLength(is3D)
              numLines = int(round(value) if mode == 'ToNumber' else math.ceil(length / value))
              len = value if mode == 'ToLength' else length / numLines

              for n, (beg, end) in enumerate([(i*len, (i+1)*len) for i in range(numLines)], 1):
                  # Snip the original curve
                  if n == numLines:
                      end = -1
                  curve.snip(fmeobjects.SNIP_DISTANCE, is3D, beg, end)

                  if outputLines:
                      line = feature.cloneAttributes()
                      line.setGeometry(curve)
                      line.setCoordSys(coordSys)
                      self.pyoutput(line)

                  if outputPoints and (0.0 < beg or outputEndNodes):
                      point = feature.cloneAttributes()
                      point.setGeometry(curve.getStartPoint())
                      point.setCoordSys(coordSys)
                      self.pyoutput(point)

                  # Restore original curve geometry
                  curve = feature.getGeometry()

              if outputEndNodes:
                  point = feature.cloneAttributes()
                  point.setGeometry(curve.getEndPoint())
                  point.setCoordSys(coordSys)
                  self.pyoutput(point)
    PYTHONSYMBOL = LineDivider
    -> GeometryFilter_2
GeometryFilter_2
    BREAK_AGG = No
    GEOM_PORT_NAMES = Point Line Arc
    POINT -> Point (output)
    LINE -> Line (output)
    ARC -> Line (output)
Line (output)
Point (output)
<Rejected> (output)
