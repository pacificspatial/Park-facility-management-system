FME workspace fn001_CityGML受入処理.fmw

Parameters:
- SourceDataset_PATH = $(FME_MF_DIR_USERTYPED)fn001_source\15202_nagaoka-shi_city_2023_citygml_1_op   # INCLUDE_WEB_BROWSER 3D都市モデルルートフォルダー
- SourceDataset_OGCGEOPACKAGE = $(FME_MF_DIR_USERTYPED)fn001_source\柵・門・看板_GS取得.gpkg   # 公共測量成果ではない都市設備 (GeoPackage)
- DestDataset_POSTGRES = postgresql-plateau-park-management   # 公園施設管理データベース (PostgreSQL)
- DEST_COORDSYS = EPSG:4326   # EnableReadFromFeature:No Destination Coordinate System

Readers:
- PATH_1: PATH from $(SourceDataset_PATH)
- OGCGEOPACKAGE_1: OGCGEOPACKAGE from $(SourceDataset_OGCGEOPACKAGE)

Writers:
- POSTGRES_1: POSTGRES to $(DestDataset_POSTGRES)

PATH (reader PATH_1)
    attributes: path_unix buffer, path_windows buffer, path_rootname buffer, path_filename buffer, path_extension buffer, path_directory_unix buffer, path_directory_windows buffer, path_type char(10)
    -> AttributeFilter_Folder
AttributeFilter_Folder
    ATTR_NAME = path_filename
    ATTR_VALUES = codelists,udx,<Empty>,<Missing>,<Null>,<Unfiltered>
    codelists -> FeatureReader_PATH_codelists [INITIATOR]
    udx -> FeatureReader_PATH_udx [INITIATOR]
FeatureReader_PATH_codelists
    ATTRIBUTES = PATH,"path_unix,path_windows,path_rootname,path_filename,path_extension,path_directory_unix,path_directory_windows,path_type,fme_geometry{0}"
    ATTR_ACCUM_MODE = Only Use Result
    COMBINE_GEOM = Use Result
    DATASET = @Value(path_unix)
    FORMAT = PATH
    ORDER_RESULTS = No
    OUTPUT_FEATURES_DISPLAY = Schema and Data Features
    PATH_GLOB_PATTERN = *.xml
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = FILE
    PATH_USE_NON_STRING_ATTR = yes
    PATH -> Tester
Note: 公園施設長寿命化計画関係コードリスト / Common_parkCode.xml / Common_parkName.xml / Common_parkType.xml / Common_parkFacilityName.xml / Common_unitOfNumberOfParkFacilities.xml / Common_parkFacilityMainMaterial.xml / Common_parkFacilityManagementType.xml / Common_parkHealthAssessmentCondition.xml / Common_parkHealthAssessmentUrgency.xml / # Common_parkRepair.xml は敢えて不使用。 / 区域関係 / Zone_function.xml
Tester
    BOOL_OP = OR
    TEST_CLAUSE:
      CASE_INSENSITIVE_TEST @Value(path_filename) IN Common_parkCode.xml,Common_parkName.xml,Common_parkType.xml,Common_parkFacilityName.xml,Common_unitOfNumberOfParkFacilities.xml,Common_parkFacilityMainMaterial.xml,Common_parkFacilityManagementType.xml
      CASE_INSENSITIVE_TEST @Value(path_filename) IN Common_parkHealthAssessmentCondition.xml,Common_parkHealthAssessmentUrgency.xml
      CASE_INSENSITIVE_TEST @Value(path_filename) IN Zone_function.xml
    TEST_MODE = CASE_INSENSITIVE_TEST
    PASSED -> FeatureReader_XML [INITIATOR]
FeatureReader_CityGML
    ATTRS_TO_EXPOSE = gml_id gml_parent_id fme_feature_type
    ATTR_ACCUM_MODE = Merge Initiator and Result
    ATTR_CONFLICT_RES = Use Result
    ATTR_IGNORE_NULLS = No
    CITYGML_ADD_NAMESPACE_PREFIX_TO_FEATURE_TYPES = No
    CITYGML_CITYGML_EXPOSE_FORMAT_ATTRS = fme_feature_type,xml_char(50)
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    COORDSYS = EPSG:4326
    DATASET = @Value(_gml_path)
    FORMAT = CITYGML
    INTERACT = NONE
    ORDER_RESULTS = No
    OUTPUT_FEATURES_DISPLAY = Schema and Data Features
    <OTHER> -> PLATEAU3.LODSplitterWithDm
PLATEAU3.LODSplitterWithDm
    DEST_COODSYS = $(DEST_COORDSYS)
    JSON_ATTRIBUTES = {}
    SRS_AXIS_ORDER_DISPLAY = 2,1,3
    LOD1 -> AttributeFilter_3
    LOD2 -> AttributeFilter_2
    LOD3 -> AttributeFilter_2
    DmGeometricAttribute -> AttributeManager_7
Note: 3D都市モデル標準製品仕様書 / "uro:ParkFacilityLongevityPlanAttribute/uro:facilityId"の定義 / 工事・点検の対象となる施設の識別子。 / 公園施設を一意に識別するコード（施設コード）を記述する。 / 公園施設の種類を表す3文字と、4桁の通し番号を公園施設の識別子とする。[記述例] BEN0001 / ENR：園路広場 / SYU：修景施設 / KYU：休養施設 / YUG：遊戯施設 / UND：運動施設 / KYO：教養施設 / BEN：便益施設 / KAN：管理施設 / SNO：その他施設 / 都市公園内の植生は、植生の種類を表す3文字と、4桁の通し番号を識別子とする。 / GRN：植生
AttributeFilter_3
    ATTR_NAME = _package
    ATTR_VALUES = wtr,<Empty>,<Missing>,<Null>,<Unfiltered>
    wtr -> Junction_5
AttributeFilter_2
    ATTR_NAME = _package
    ATTR_VALUES = frn,bldg,brid,trk,<Empty>,<Missing>,<Null>,<Unfiltered>
    frn -> Junction_5
    bldg -> Junction_4
    brid -> Junction_4
    trk -> 2DForcer_2
Junction_5
    -> AttributeKeeper
AttributeKeeper
    CREATE_BULK_MODE_FEATURES = NO
    KEEP_ATTRS = gml_id,_package
    -> Junction
Junction_4
    -> Tester_4
2DForcer_2
    2D -> Tester_4
Tester_4
    BOOL_OP = OR
    TEST_CLAUSE = TEST @Value(fme_feature_type) NOT_IN Building,Bridge
    TEST_MODE = TEST
    PASSED -> Aggregator
Aggregator
    ACCUM_ATTRS_NAME = Drop Incoming Attributes
    AGGREGATE_TYPE = Homogeneous Collection (If Possible)
    GROUP_BY = gml_parent_id _package
    MODE = Geometry - Assemble One Level
    SEP = ,
    AGGREGATE -> AttributeRenamer
AttributeRenamer
    ATTR_TABLE = RENAME_SET_DEFAULT gml_parent_id > gml_id
    MISSING_INPUT_ATTRS = REMOVE
    -> Junction
Junction
    -> FeatureMerger [SUPPLIER]
Note: 公園施設（3D） / bldg 建築物 LOD2 / brid 橋梁 LOD2 / frn 都市設備 LOD2, LOD3 / wtr 水部 LOD1 / 公園施設（2D） / trk 徒歩道 LOD2 / frn 都市設備 DmGeometricAttribute / frn-ext 都市設備（公共測量成果ではないもの） / 単木（3D） / veg 植生 LOD3 (SolitaryVegetationObject)
Note: FeatureReader_CityGML_area : Initiator
Junction_11
    -> Junction_12
Note: AttributeFilter : area
Junction_12
    -> FeatureReader_CityGML_area [INITIATOR]
Note: 公園コード park_code text / 公園名 park_name text / 公園種別 park_type text / 施設コード facility_code text / 表示無し previous_facility_code text ??? / 公園施設種類【選択】 facility_type text <- 施設コード先頭3文字から変換 / 公園施設名【選択】 facility_name text / 公園施設名（任意） facility_name_optional text / 具体的施設名称 specific_facility_name text / 数量（数値） quantity_numeric integer / 数量（単位【選択】) quantity_unit text / 規模 size text / 主要部材【選択】 main_material text / 主要部材（任意） main_material_optional text / 設置年度 installation_year integer
Junction_2
    -> Junction_6
AttributeValueMapper
    DEFAULT_VALUE = （不明）
    LUT = ENR,園路広場,SYU,修景施設,KYU,休養施設,YUG,遊戯施設,UND,運動施設,KYO,教養施設,BEN,便益施設,KAN,管理施設,SNO,その他施設,GRN,植生
    MAPPING_DIRECTION = FORWARD
    SRC = facility_type
    VAL_ATTR = facility_type
    -> GeometryRemover
AttributeKeeper_2
    CREATE_BULK_MODE_FEATURES = NO
    KEEP_ATTRS = _package,facility_code,gml_id
    -> FeatureMerger [REQUESTOR]
FeatureMerger
    GROUP_BY = _package
    JOIN_KEYS = @Value(gml_id) @Value(gml_id) AUTO
    MERGE_TYPE = Geometry
    PROCESS_DUPS = NO
    REJECT_NULL_MISSING_KEYS = No
    SUPPLIERS_FIRST = No
    MERGED -> Aggregator_2
Note: PythonCaller_2 : Input
Junction_9
    -> Junction_10
Note: PythonCaller_3 : Input
Junction_13
    -> Junction_14
Note: GeometryRefiner : Input
Junction_15
    -> Junction_16
Note: PROJReprojector_2 : Reprojected
Junction_16
    -> GeometryRefiner
2DForcer_3
    2D -> ParameterFetcher
ParameterFetcher
    ATTR_LIST = _coordsys $(DEST_COORDSYS)
    -> CoordinateSystemDescriptionConverter
CoordinateSystemDescriptionConverter
    DIRECTION_LONG = Convert From FME Representation
    KIND_LONG = PROJ.4 String
    SRC = _coordsys
    VAL_ATTR = _coordsys
    -> PROJReprojector
PROJReprojector
    DEST = @Value(_coordsys)
    INTERPOLATION_TYPE_NAME = Nearest Neighbor
    RASTER_CELL_SIZE = Preserve Cells
    RASTER_TOLERANCE = 0.0
    TRANSFORM_TYPE = Automatic Transformation
    REPROJECTED -> Junction_3
Junction_3
    -> Aggregator_2
Aggregator_2
    ACCUM_ATTRS_NAME = Drop Incoming Attributes
    AGGREGATE_TYPE = Homogeneous Collection (If Possible)
    GROUP_BY = _package facility_code
    MODE = Geometry - Assemble One Level
    SEP = ,
    AGGREGATE -> GeometryRefiner
GeometryRefiner
    -> DimensionExtractor
DimensionExtractor
    DIM_ATTR = _dimension
    -> Sorter
Sorter
    SORT_PARM = _package ALPHA ASCENDING facility_code ALPHA ASCENDING
    SORTED -> TempPathnameCreator
Note: 施設コードがあるもの (管理対象施設・樹木）は facility_code、その他（区域）については attrib (JSON属性セット) を設定する。
echigo_facility_geometry (writer POSTGRES_1)
    attributes: package varchar, facility_code varchar, dimension int2, coordsys varchar, fbx_binary bytea, attrib json
Note: GeometryRemover : Input
Junction_7
    -> Junction_8
Note: fence-gate-signboard (frn-ext)
Junction_8
    -> GeometryRemover
GeometryRemover
    REMOVE_COORDSYS = No
    -> DuplicateFilter
DuplicateFilter
    INPUT_ORDERED_CHOICE = No
    KEYATTR = facility_code
    UNIQUE -> Sorter_2
Note: 健全度調査以前に実施した補修の有無 / bool -> int2 に変更 / repairs_before_healthcheck_exists / 1: 施設の設置から今回の健全度調査までに補修を実施した / 2: 施設の設置から今回の健全度調査までに補修を実施していない / 3: 施設の設置から今回の健全度調査までに補修を実施しているか不明
Sorter_2
    SORT_PARM = _package ALPHA ASCENDING facility_code ALPHA ASCENDING
    SORTED -> AttributeManager_10
AttributeManager_10
    ATTR_TABLE:
      REMOVE _package (buffer)
      REMOVE gml_id (buffer)
      RENAME_SET_VALUE expected_renewal_year_with_measures > updated_year_with_measures (buffer)
    -> echigo_facility_table (writer POSTGRES_1)
echigo_facility_table (writer POSTGRES_1)
    attributes: park_code text, park_name text, park_type text, facility_code text,PrimaryKey, previous_facility_code text, facility_type text, facility_name text, facility_name_optional text, specific_facility_name text, quantity_numeric int4, quantity_unit text, size text, main_material text, main_material_optional text, installation_year int4, elapsed_years int4, disposal_limit_period int4, expected_usage_period int4, repairs_before_healthcheck_exists int2, repairs_before_healthcheck_year int4, health_check_year int4, health_check_deterioration_status text, health_check_condition text, health_check_urgency text, management_type text, updated_year_with_measures int4, cost_2020_thousand_yen int4, content_2020 text, cost_2021_thousand_yen int4, content_2021 text,
      cost_2022_thousand_yen int4, content_2022 text, cost_2023_thousand_yen int4, content_2023 text, cost_2024_thousand_yen int4, content_2024 text, cost_2025_thousand_yen int4, content_2025 text, cost_2026_thousand_yen int4, content_2026 text, cost_2027_thousand_yen int4, content_2027 text, cost_2028_thousand_yen int4, content_2028 text, cost_2029_thousand_yen int4, content_2029 text, note_for_longevity text, color text

Bookmark: コードリスト辞書作成
FeatureReader_XML
    ATTRIBUTES = Definition,"Definition.id,description,name,xml_fragment,xml_id,xml_matched_element,xml_parent_child_pos,xml_parent_id,fme_basename"
    ATTR_ACCUM_MODE = Only Use Result
    COMBINE_GEOM = Use Result
    DATASET = @Value(path_unix)
    FORMAT = XML
    INTERACT = NONE
    ORDER_RESULTS = No
    OUTPUT_FEATURES_DISPLAY = Schema and Data Features
    XML_CONTINUE_ON_GEOM_ERROR = no
    XML_FILE_TYPE = Feature Paths
    XML_IGNORE_DATASET_EXTERNAL_DTD = no
    XML_SUPPORTED_READER_ARCHIVE_EXTENSIONS = xml.gz,gml.gz
    XML_USE_SEARCH_ENVELOPE = NO
    XML_VALIDATE_DATASET = no
    XML_VALIDATE_XFMAP = no
    XML_XFMAP_FEATURE_PATHS = Dictionary/dictionaryEntry/Definition
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    XML_XML_EXPOSE_FORMAT_ATTRS = fme_basename,xml_char(50)
    Definition -> AttributeKeeper_3
AttributeKeeper_3
    CREATE_BULK_MODE_FEATURES = NO
    KEEP_ATTRS = description,fme_basename,name
    -> Sampler
Sampler
    GROUP_BY = fme_basename
    RATE = 1
    SAMPLE_MODE = No
    SAMPLE_TYPE_LONG = First N Features
    SAMPLED -> JSONTemplater [SUB]
    SAMPLED -> JSONTemplater [SUB_2]
    NOT_SAMPLED -> JSONTemplater [SUB_2]
Creator
    GEOMTYPE = Geometry Object
    NUM = 1
    CREATED -> JSONTemplater [ROOT]
JSONTemplater
    RESULT_ATTRIBUTE = _codelists_json
    ROOT_QUERY_EXPR = {| fme:process-features("SUB") |}
    SUB_2_QUERY_EXPR = {fme:get-attribute("name") : fme:get-attribute("description")}
    SUB_QUERY_EXPR:
      {
          fme:get-attribute("fme_basename")||'.xml' : {|
              fme:process-features(
                  "SUB_2",
                  'fme_basename',
                  fme:get-attribute("fme_basename")
              )
          |}
      }
    VISIBLE_QUERY_VALIDATE = Yes
    -> Junction_2
    -> Junction_9
    -> Junction_13

Bookmark: 3D都市モデルデータセット内で公園長寿命化計画で使用するパッケージフォルダーを選択
FeatureReader_PATH_udx
    ATTRIBUTES = PATH,"path_unix,path_windows,path_rootname,path_filename,path_extension,path_directory_unix,path_directory_windows,path_type,fme_geometry{0}"
    ATTR_ACCUM_MODE = Only Use Result
    COMBINE_GEOM = Use Result
    DATASET = @Value(path_unix)
    FORMAT = PATH
    ORDER_RESULTS = No
    OUTPUT_FEATURES_DISPLAY = Schema and Data Features
    PATH_GLOB_PATTERN = *
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = DIRECTORY
    PATH_USE_NON_STRING_ATTR = yes
    PATH -> AttributeManager
AttributeManager
    ATTR_TABLE:
      RENAME_SET_VALUE path_unix > _package_path (buffer)
      REMOVE path_windows (buffer)
      REMOVE path_rootname (buffer)
      RENAME_SET_VALUE path_filename > _package (buffer)
      REMOVE path_extension (buffer)
      REMOVE path_directory_unix (buffer)
      REMOVE path_directory_windows (buffer)
      REMOVE path_type (varchar(10))
    -> AttributeFilter
AttributeFilter
    ATTR_NAME = _package
    ATTR_VALUES = bldg,brid,frn,trk,urf,wtr,veg,area,<Empty>,<Missing>,<Null>,<Unfiltered>
    area -> Junction_11
    bldg -> FeatureReader_PATH [INITIATOR]
    brid -> FeatureReader_PATH [INITIATOR]
    frn -> FeatureReader_PATH [INITIATOR]
    trk -> FeatureReader_PATH [INITIATOR]
    urf -> FeatureReader_PATH [INITIATOR]
    wtr -> FeatureReader_PATH [INITIATOR]
    veg -> FeatureReader_PATH [INITIATOR]

Bookmark: 公園長寿命化計画関係属性を持つ公園施設および単独木 (SolitaryVegetationObject) を抽出
FeatureReader_PATH
    ATTRIBUTES = PATH,"path_unix,path_windows,path_rootname,path_filename,path_extension,path_directory_unix,path_directory_windows,path_type,fme_geometry{0}"
    ATTR_ACCUM_MODE = Merge Initiator and Result
    ATTR_CONFLICT_RES = Use Result
    ATTR_IGNORE_NULLS = No
    COMBINE_GEOM = Use Result
    DATASET = @Value(_package_path)
    FORMAT = PATH
    ORDER_RESULTS = No
    OUTPUT_FEATURES_DISPLAY = Schema and Data Features
    PATH_GLOB_PATTERN = *.gml
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = FILE
    PATH_USE_NON_STRING_ATTR = yes
    PATH -> AttributeManager_2
AttributeManager_2
    ATTR_TABLE:
      REMOVE _package_path (buffer)
      RENAME_SET_VALUE path_unix > _gml_path (buffer)
      REMOVE path_windows (buffer)
      REMOVE path_rootname (buffer)
      REMOVE path_filename (buffer)
      REMOVE path_extension (buffer)
      REMOVE path_directory_unix (buffer)
      REMOVE path_directory_windows (buffer)
      REMOVE path_type (varchar(10))
      REMOVE fme_geometry{0} (fme_no_geom)
      REMOVE fme_geometry{} (varchar(200))
    -> XMLXQueryExtractor
XMLXQueryExtractor
    QUERY_EXPR:
      declare namespace uro="https://www.geospatial.jp/iur/uro/3.0";
      count(//uro:ParkFacilityLongevityPlanAttribute)
    RESULT_ATTRIBUTE = _result
    RESULT_TYPE_NAME = Single value
    WRITE_XML_HEADER = No
    XML_FILE = @Value(_gml_path)
    XML_TYPE = XML file
    XQUERY_TYPE = XQuery expression
    QUERY_RESULTS -> TestFilter
TestFilter
    DEFAULT_VALUE = <UNFILTERED>
    PASSED_TEST_GROUP_OUTPUT = FIRST
    TEST_LIST = "BOOL_OP,OR,COMPOSITE_TEST,""""""1"""""",TEST_CLAUSE,TEST 0 < @Value(_result)",公園施設あり,"BOOL_OP,OR,COMPOSITE_TEST,""""""1"""""",TEST_CLAUSE,TEST @Value(_package) = veg",植生モデル
    公園施設あり -> XMLFragmenter
    公園施設あり -> FeatureReader_CityGML [INITIATOR]
    植生モデル -> FeatureReader_CityGML_veg [INITIATOR]

Bookmark: 公園施設長寿命化計画関係属性抽出
XMLFragmenter
    EMBEDDED_EXPRESSIONS = cityObjectMember/*
    FEATURE_TYPES_FORMAT_NAME = XML
    FILE_XML = @Value(_gml_path)
    IGNORE_DATASET_EXTERNAL_DTD = No
    MERGE_ATTRS = Yes
    REJECT_FEATURES_WITH_NO_FRAGMENTS = YES
    XML_SOURCE_TYPE = XML File or URL
    FRAGMENTS -> XMLXQueryExtractor_2
XMLXQueryExtractor_2
    NEW_ATTRIBUTES = gml_id
    QUERY_EXPR:
      declare namespace gml="http://www.opengis.net/gml";
      declare namespace uro="https://www.geospatial.jp/iur/uro/3.0";
      let $x := //uro:ParkFacilityLongevityPlanAttribute
      return if ($x) then
      (
          $x,
          fme:set-attribute('gml_id', data(/*/@gml:id))
      )
      else 'none'
    RESULT_ATTRIBUTE = xml_fragment
    RESULT_TYPE_NAME = Single value
    WRITE_XML_HEADER = No
    XML_ATTR = xml_fragment
    XML_REMOVE_SOURCE_ATTR = No
    XML_TYPE = Attribute specifying XML
    XQUERY_TYPE = XQuery expression
    QUERY_RESULTS -> Tester_2
Tester_2
    BOOL_OP = OR
    TEST_CLAUSE = TEST gml_id ATTRIBUTE_HAS_A_VALUE ""
    TEST_MODE = TEST
    PASSED -> XMLFlattener
XMLFlattener
    ATTRIBUTE_XML = xml_fragment
    EMBEDDED_EXPRESSIONS = ParkFacilityLongevityPlanAttribute
    FEATURE_TYPES_FORMAT_NAME = XML
    FLATTEN_OPTIONS:
      <structure
      separator="."
      open-list-brace="{"
      close-list-brace="}"
      map-empty-elements="yes"
      matched-prefix="attributes"
      matched-attributes="yes"
      matched-ancestor-attributes=""
      cardinality="*/parkHealthAssessment{}/+
      +{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    IGNORE_DATASET_EXTERNAL_DTD = No
    XML_SOURCE_TYPE = Attribute with XML document
    -> PythonCaller
Junction_6
    -> PythonCaller
Note: 長寿命化対策属性抽出 / コード->意味文字列置換
PythonCaller
    HIDE_ATTRIBUTES = _codelists_json
    PYTHONSOURCE:
      import fme
      import fmeobjects, json


      class FeatureProcessor(object):
          def __init__(self):
              self.features = []
              self.codelists = None

          def has_support_for(self, support_type: int):
              return support_type == fmeobjects.FME_SUPPORT_FEATURE_TABLE_SHIM

          def input(self, feature: fmeobjects.FMEFeature):
              _, missing, _ = feature.getAttributeNullMissingAndType('_codelists_json')
              if missing:
                  prefix = 'longevityMeasures{}.LongevityMeasures.'
                  year = feature.getAttribute(prefix + 'fiscalYearForCountermeasures')
                  cost = feature.getAttribute(prefix + 'countermeasuresCost.CountermeasuresCost.cost')
                  desc = feature.getAttribute(prefix + 'description')
                  if year and cost and desc:
                      for y, c, d in zip(year, cost, desc):
                          feature.setAttribute('cost_%s_thousand_yen' % y, c)
                          feature.setAttribute('content_%s' % y , d)
                  self.features.append(feature)
              else:
                  self.codelists = json.loads(feature.getAttribute('_codelists_json'))

          def close(self):
              import re
              pattern = re.compile(r'^(.+)\.codeSpace$')
              for feature in self.features:
                  for attr in feature.getAllAttributeNames():
                      m = pattern.match(attr)
                      if m:
                          basename = m.group(1)
                          codelist = feature.getAttribute(attr).split('/')[-1]
                          d = self.codelists.get(codelist, {})
                          code = feature.getAttribute(basename)
                          value = d.get(code, code)
                          feature.setAttribute(basename, value)
                          feature.setAttribute('%s_code' % basename, code)
                  self.pyoutput(feature)

          def process_group(self):
              pass
    PYTHONSYMBOL = FeatureProcessor
    -> AttributeExposer
AttributeExposer
    ATTR_TABLE = facilityId,buffer,parkCode,buffer,parkCode_code,buffer,parkCode.codeSpace,buffer,parkName,buffer,parkName_code,buffer,parkName.codeSpace,buffer,parkType,buffer,parkType_code,buffer,parkType.codeSpace,buffer,facilityName,buffer,facilityName_code,buffer,facilityName.codeSpace,buffer,facilityNameOptional,buffer,specificFacilityName,buffer,numberOfFacilities.NumberOfFacilities.quantity,buffer,numberOfFacilities.NumberOfFacilities.quantityUnit,buffer,numberOfFacilities.NumberOfFacilities.quantityUnit_code,buffer,numberOfFacilities.NumberOfFacilities.quantityUnit.codeSpace,buffer,size,buffer,mainMaterial,buffer,mainMaterial_code,buffer,mainMaterial.codeSpace,buffer,mainMaterialOptional,buffer,installationYear,buffer,disposalLimitPeriod,buffer,expectedUsagePeriod,buffer,expectedRenewalYearWithMeasures,buffer,managementType,buffer,managementType_code,buffer,managementType.codeSpace,buffer,repairsBeforeParkHealthAssessment.RepairsBeforeParkHealthAssessment.repair,buffer,repairsBeforeParkHealthAssessment.RepairsBeforeParkHealthAssessment.repairFiscalYear,buffer,parkHealthAssessment{}.ParkHealthAssessment.assessmentFiscalYear,buffer,parkHealthAssessment{}.ParkHealthAssessment.deteriorationStatus,buffer,parkHealthAssessment{}.ParkHealthAssessment.condition,buffer,parkHealthAssessment{}.ParkHealthAssessment.condition_code,buffer,parkHealthAssessment{}.ParkHealthAssessment.condition.codeSpace,buffer,parkHealthAssessment{}.ParkHealthAssessment.urgency,buffer,parkHealthAssessment{}.ParkHealthAssessment.urgency_code,buffer,parkHealthAssessment{}.ParkHealthAssessment.urgency.codeSpace,buffer,longevityMeasures{}.LongevityMeasures.countermeasuresCost.CountermeasuresCost.cost,buffer,longevityMeasures{}.LongevityMeasures.countermeasuresCost.CountermeasuresCost.costUnit,buffer,longevityMeasures{}.LongevityMeasures.description,buffer,longevityMeasures{}.LongevityMeasures.fiscalYearForCountermeasures,buffer,content_2020,buffer,content_2021,buffer,content_2022,buffer,content_2023,buffer,content_2024,buffer,content_2025,buffer,content_2026,buffer,content_2027,buffer,content_2028,buffer,content_2029,buffer,cost_2020_thousand_yen,buffer,cost_2021_thousand_yen,buffer,cost_2022_thousand_yen,buffer,cost_2023_thousand_yen,buffer,cost_2024_thousand_yen,buffer,cost_2025_thousand_yen,buffer,cost_2026_thousand_yen,buffer,cost_2027_thousand_yen,buffer,cost_2028_thousand_yen,buffer,cost_2029_thousand_yen,buffer,noteForLongEvity,buffer
    -> ListSorter
ListSorter
    ORDER = Descending
    SRC_LIST = parkHealthAssessment{}.ParkHealthAssessment.assessmentFiscalYear
    TYPE = Numeric
    -> ListIndexer
ListIndexer
    INDEX = 0
    LIST_ATTR = parkHealthAssessment{}
    -> AttributeManager_8
AttributeManager_8
    ATTR_TABLE:
      REMOVE _gml_path (buffer)
      REMOVE _result (buffer)
      REMOVE xml_fragment (buffer)
      REMOVE xml_id (uint32)
      REMOVE xml_matched_element (buffer)
      REMOVE xml_parent_id (uint32)
      REMOVE xml_parent_child_pos (uint32)
      RENAME_SET_VALUE parkCode > park_code (buffer)
      RENAME_SET_VALUE parkName > park_name (buffer)
      RENAME_SET_VALUE parkType > park_type (buffer)
      RENAME_SET_VALUE facilityId > facility_code (buffer)
      SET_TO facility_type (buffer) = @Left(@Value(facility_code),3)
      RENAME_SET_VALUE facilityName > facility_name (buffer)
      RENAME_SET_VALUE facilityNameOptional > facility_name_optional (buffer)
      RENAME_SET_VALUE specificFacilityName > specific_facility_name (buffer)
      RENAME_SET_VALUE numberOfFacilities.NumberOfFacilities.quantity > quantity_numeric (int32)
      RENAME_SET_VALUE numberOfFacilities.NumberOfFacilities.quantityUnit > quantity_unit (buffer)
      RENAME_SET_VALUE mainMaterial > main_material (buffer)
      RENAME_SET_VALUE mainMaterialOptional > main_material_optional (buffer)
      RENAME_SET_VALUE installationYear > installation_year (int16)
      RENAME_SET_VALUE disposalLimitPeriod > disposal_limit_period (buffer)
      RENAME_SET_VALUE expectedUsagePeriod > expected_usage_period (buffer)
      RENAME_SET_VALUE repairsBeforeParkHealthAssessment.RepairsBeforeParkHealthAssessment.repair > repairs_before_healthcheck_exists (int8)
      RENAME_SET_VALUE repairsBeforeParkHealthAssessment.RepairsBeforeParkHealthAssessment.repairFiscalYear > repairs_before_healthcheck_year (int16)
      RENAME_SET_VALUE ParkHealthAssessment.assessmentFiscalYear > health_check_year (int16)
      RENAME_SET_VALUE ParkHealthAssessment.deteriorationStatus > health_check_deterioration_status (buffer)
      RENAME_SET_VALUE ParkHealthAssessment.condition > health_check_condition (buffer)
      RENAME_SET_VALUE ParkHealthAssessment.urgency > health_check_urgency (buffer)
      RENAME_SET_VALUE managementType > management_type (buffer)
      RENAME_SET_VALUE expectedRenewalYearWithMeasures > expected_renewal_year_with_measures (int16)
      REMOVE parkCode_code (buffer)
      REMOVE parkCode.codeSpace (buffer)
      REMOVE parkName_code (buffer)
      REMOVE parkName.codeSpace (buffer)
      REMOVE parkType_code (buffer)
      REMOVE parkType.codeSpace (buffer)
      REMOVE facilityName_code (buffer)
      REMOVE facilityName.codeSpace (buffer)
      REMOVE numberOfFacilities.NumberOfFacilities.quantityUnit_code (buffer)
      REMOVE numberOfFacilities.NumberOfFacilities.quantityUnit.codeSpace (buffer)
      REMOVE mainMaterial_code (buffer)
      REMOVE mainMaterial.codeSpace (buffer)
      REMOVE managementType_code (buffer)
      REMOVE managementType.codeSpace (buffer)
      REMOVE parkHealthAssessment{}.ParkHealthAssessment.assessmentFiscalYear (buffer)
      REMOVE parkHealthAssessment{}.ParkHealthAssessment.deteriorationStatus (buffer)
      REMOVE parkHealthAssessment{}.ParkHealthAssessment.condition (buffer)
      REMOVE parkHealthAssessment{}.ParkHealthAssessment.condition_code (buffer)
      REMOVE parkHealthAssessment{}.ParkHealthAssessment.condition.codeSpace (buffer)
      REMOVE parkHealthAssessment{}.ParkHealthAssessment.urgency (buffer)
      REMOVE parkHealthAssessment{}.ParkHealthAssessment.urgency_code (buffer)
      REMOVE parkHealthAssessment{}.ParkHealthAssessment.urgency.codeSpace (buffer)
      REMOVE ParkHealthAssessment.condition_code (buffer)
      REMOVE ParkHealthAssessment.condition.codeSpace (buffer)
      REMOVE ParkHealthAssessment.urgency_code (buffer)
      REMOVE ParkHealthAssessment.urgency.codeSpace (buffer)
      REMOVE longevityMeasures{}.LongevityMeasures.countermeasuresCost.CountermeasuresCost.cost (buffer)
      REMOVE longevityMeasures{}.LongevityMeasures.countermeasuresCost.CountermeasuresCost.costUnit (buffer)
      REMOVE longevityMeasures{}.LongevityMeasures.description (buffer)
      REMOVE longevityMeasures{}.LongevityMeasures.fiscalYearForCountermeasures (buffer)
      RENAME_SET_VALUE noteForLongEvity > note_for_longevity (buffer)
    -> AttributeKeeper_2
    -> AttributeValueMapper

Bookmark: 柵・門・看板 fence-gate-signboard
AttributeManager_7
    ATTR_TABLE:
      REMOVE dm_feature_type (buffer)
      REMOVE dm_attributes_xml (buffer)
      REMOVE dm_attributes_json (varchar(200))
      REMOVE dm_dmCode (buffer)
      REMOVE dm_dmCode_code (buffer)
      REMOVE dm_geometryType (buffer)
      REMOVE dm_geometryType_code (buffer)
      REMOVE dm_mapLevel (buffer)
      REMOVE dm_mapLevel_code (buffer)
      REMOVE dm_shapeType (buffer)
      REMOVE dm_shapeType_code (buffer)
      REMOVE _geometry_name (buffer)
      REMOVE _lod (varchar(200))
      REMOVE _gml_path (buffer)
      REMOVE _result (buffer)
      REMOVE gml_parent_id (buffer)
      REMOVE fme_feature_type (buffer)
    -> 2DForcer
2DForcer
    2D -> Junction

Bookmark: 植生のうちLOD3単独木（SolitaryVegetationObject）
FeatureReader_CityGML_veg
    ATTRIBUTES = CityModel,"gml_id,citygml_target_uri,gml_description,gml_name,citygml_city_object_member{}.xlink_href,citygml_appearance_member{}.xlink_href,gml_feature_member{}.xlink_href,fme_feature_type",PlantCover,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,uro_veg_dm_attribute{},uro_veg_facility_attribute{},uro_veg_facility_id_attribute{},uro_veg_facility_type_attribute{},uro_vegetation_data_quality_attribute{},citygml_class,citygml_class_codeSpace,citygml_function{},citygml_function{}.codeSpace,citygml_usage{},citygml_usage{}.codeSpace,citygml_average_height,citygml_average_height_units,citygml_level_of_detail{},施設コード,fme_feature_type",SolitaryVegetationObject,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,uro_veg_dm_attribute{},uro_veg_facility_attribute{},uro_veg_facility_id_attribute{},uro_veg_facility_type_attribute{},uro_vegetation_data_quality_attribute{},citygml_class,citygml_class_codeSpace,citygml_function{},citygml_function{}.codeSpace,citygml_usage{},citygml_usage{}.codeSpace,citygml_species,citygml_species_codeSpace,citygml_height,citygml_height_units,citygml_trunk_diameter,citygml_trunk_diameter_units,citygml_crown_diameter,citygml_crown_diameter_units,citygml_level_of_detail{},施設コード,fme_feature_type"
    ATTRS_TO_EXPOSE = gml_id gml_parent_id fme_feature_type
    ATTR_ACCUM_MODE = Merge Initiator and Result
    ATTR_CONFLICT_RES = Use Result
    ATTR_IGNORE_NULLS = No
    CITYGML_ADD_NAMESPACE_PREFIX_TO_FEATURE_TYPES = No
    CITYGML_CITYGML_EXPOSE_FORMAT_ATTRS = fme_feature_type,xml_char(50)
    CITYGML_GENERIC_ATTRS_AS_FEATURES = No
    CITYGML_GENERIC_ATTRS_AS_SCHEMA_ATTRS = Yes
    CITYGML_LODS_TO_READ = 3
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    COORDSYS = EPSG:4326
    DATASET = @Value(_gml_path)
    FEATURETYPES = SolitaryVegetationObject
    FORMAT = CITYGML
    INTERACT = NONE
    ORDER_RESULTS = No
    OUTPUT_FEATURES_DISPLAY = Schema and Data Features
    SolitaryVegetationObject -> AttributeManager_4
AttributeManager_4
    ATTR_TABLE:
      RENAME_SET_VALUE 施設コード > facility_code (buffer)
      REMOVE _gml_path (buffer)
      REMOVE _result (buffer)
      REMOVE gml_id (buffer)
      REMOVE gml_parent_id (buffer)
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (xml)
      REMOVE externalReference{}.externalObject.uri (xml)
      REMOVE externalReference{}.informationSystem (xml)
      REMOVE citygml_generalizes_to{}.xlink_href (buffer)
      REMOVE citygml_relative_to_terrain (varchar(33))
      REMOVE citygml_relative_to_water (varchar(38))
      REMOVE citygml_appearance{}.xlink_href (buffer)
      REMOVE uro_veg_dm_attribute{} (xml)
      REMOVE uro_veg_facility_attribute{} (xml)
      REMOVE uro_veg_facility_id_attribute{} (xml)
      REMOVE uro_veg_facility_type_attribute{} (xml)
      REMOVE uro_vegetation_data_quality_attribute{} (xml)
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_species (buffer)
      REMOVE citygml_species_codeSpace (buffer)
      REMOVE citygml_height (real64)
      REMOVE citygml_height_units (buffer)
      REMOVE citygml_trunk_diameter (real64)
      REMOVE citygml_trunk_diameter_units (buffer)
      REMOVE citygml_crown_diameter (real64)
      REMOVE citygml_crown_diameter_units (buffer)
      REMOVE citygml_level_of_detail{} (buffer)
      REMOVE fme_feature_type (varchar(50))
    -> ParameterFetcher

Bookmark: 区域
FeatureReader_CityGML_area
    ATTRIBUTES = CityModel,"gml_id,citygml_target_uri,gml_description,gml_name,citygml_city_object_member{}.xlink_href,citygml_appearance_member{}.xlink_href,gml_feature_member{}.xlink_href",Zone,"gml_id,gml_parent_id,citygml_target_uri,citygml_feature_role,citygml_feature_role_attr_name,citygml_feature_role_attr_val,gml_description,gml_name,citygml_creationDate,citygml_terminationDate,externalReference{}.externalObject.name,externalReference{}.externalObject.uri,externalReference{}.informationSystem,citygml_generalizes_to{}.xlink_href,citygml_relative_to_terrain,citygml_relative_to_water,citygml_appearance{}.xlink_href,urf_class,urf_class_codeSpace,urf_function{},urf_function{}.codeSpace,urf_usage{},urf_usage{}.codeSpace,urf_valid_from,urf_valid_from_type,urf_valid_from_type_codeSpace,urf_enactment_fiscal_year,urf_valid_to,urf_valid_to_type,urf_valid_to_type_codeSpace,urf_expiration_fiscal_year,urf_legal_grounds,urf_custodian,urf_notification_number,urf_final_notification_date,urf_final_notification_number,urf_urban_plan_type,urf_urban_plan_type_codeSpace,urf_area_classification_type,urf_area_classification_type_codeSpace,urf_nominal_area,urf_nominal_area_units,urf_prefecture,urf_prefecture_codeSpace,urf_city,urf_city_codeSpace,urf_reference,urf_reason,urf_reason_xlink_href,urf_note,urf_note_xlink_href,urf_survey_year,citygml_level_of_detail{},urf_target{}.xlink_href,urf_boundary{},urf_location,urf_urban_park_attribute"
    ATTR_ACCUM_MODE = Merge Initiator and Result
    ATTR_CONFLICT_RES = Use Result
    ATTR_IGNORE_NULLS = No
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 1
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(_package_path)/*.gml
    FEATURETYPES = Zone
    FORMAT = CITYGML
    INTERACT = NONE
    ORDER_RESULTS = No
    OUTPUT_FEATURES_DISPLAY = Schema and Data Features
    Zone -> XMLFlattener_2
XMLFlattener_2
    ATTRIBUTE_XML = urf_urban_park_attribute
    EMBEDDED_EXPRESSIONS = UrbanParkAttribute
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    IGNORE_DATASET_EXTERNAL_DTD = No
    XML_SOURCE_TYPE = Attribute with XML document
    -> PythonCaller_3
Note: JSONTemplater : Output
Junction_14
    -> PythonCaller_3
Note: コード->意味文字列置換
PythonCaller_3
    HIDE_ATTRIBUTES = _codelists_json
    PYTHONSOURCE:
      import fme
      import fmeobjects, json

      class CodeReplacer_area(object):
          def __init__(self):
              self.features = []
              self.codelists = None

          def has_support_for(self, support_type: int):
              return support_type == fmeobjects.FME_SUPPORT_FEATURE_TABLE_SHIM

          def input(self, feature: fmeobjects.FMEFeature):
              _, missing, _ = feature.getAttributeNullMissingAndType('_codelists_json')
              if missing:
                  self.features.append(feature)
              else:
                  self.codelists = json.loads(feature.getAttribute('_codelists_json'))

          def close(self):
              import re
              pattern = re.compile(r'^(.+)\.codeSpace$')
              for feature in self.features:
                  for attr in feature.getAllAttributeNames():
                      m = pattern.match(attr)
                      if m:
                          basename = m.group(1)
                          codelist = feature.getAttribute(attr).split('/')[-1]
                          d = self.codelists.get(codelist, {})
                          code = feature.getAttribute(basename)
                          value = d.get(code, code)
                          feature.setAttribute(basename, value)
                          feature.setAttribute('%s_code' % basename, code)
                  self.pyoutput(feature)

          def process_group(self):
              pass
    PYTHONSYMBOL = CodeReplacer_area
    -> AttributeExposer_2
AttributeExposer_2
    ATTR_TABLE = breakdownOfNominalArea.BreakdownOfNominalArea.areaInSquareMeter,buffer,breakdownOfNominalArea.BreakdownOfNominalArea.areaInSquareMeter.uom,buffer,breakdownOfNominalArea.BreakdownOfNominalArea.breakdown,buffer,parkCode,buffer,parkCode.codeSpace,buffer,startFrom,buffer,urf_function{0},buffer,urf_function{0}.codeSpace,buffer
    -> AttributeManager_5
AttributeManager_5
    ATTR_TABLE:
      SET_TO feature_type (buffer) = Zone
      RENAME_SET_VALUE gml_name > name (buffer)
      REMOVE parkCode (buffer)
      RENAME_SET_VALUE urf_function{0} > function (buffer)
      RENAME_SET_VALUE urf_nominal_area > nominalArea (real64)
      RENAME_SET_VALUE urf_location > location (buffer)
      RENAME_SET_VALUE startFrom (buffer)
      REMOVE urf_nominal_area_units (buffer)
      REMOVE breakdownOfNominalArea.BreakdownOfNominalArea.areaInSquareMeter (buffer)
      REMOVE breakdownOfNominalArea.BreakdownOfNominalArea.areaInSquareMeter.uom (buffer)
      REMOVE breakdownOfNominalArea.BreakdownOfNominalArea.breakdown (buffer)
      REMOVE parkCode.codeSpace (buffer)
      REMOVE urf_function{0}.codeSpace (buffer)
      REMOVE urf_function{} (buffer)
      REMOVE urf_function{}.codeSpace (buffer)
      REMOVE gml_id (buffer)
      REMOVE gml_parent_id (buffer)
      REMOVE citygml_target_uri (buffer)
      REMOVE citygml_feature_role (buffer)
      REMOVE citygml_feature_role_attr_name (buffer)
      REMOVE citygml_feature_role_attr_val (buffer)
      REMOVE gml_description (buffer)
      REMOVE citygml_creationDate (buffer)
      REMOVE citygml_terminationDate (buffer)
      REMOVE externalReference{}.externalObject.name (xml)
      REMOVE externalReference{}.externalObject.uri (xml)
      REMOVE externalReference{}.informationSystem (xml)
      REMOVE citygml_generalizes_to{}.xlink_href (buffer)
      REMOVE citygml_relative_to_terrain (varchar(33))
      REMOVE citygml_relative_to_water (varchar(38))
      REMOVE citygml_appearance{}.xlink_href (buffer)
      REMOVE urf_class (buffer)
      REMOVE urf_class_codeSpace (buffer)
      REMOVE urf_usage{} (buffer)
      REMOVE urf_usage{}.codeSpace (buffer)
      REMOVE urf_valid_from (buffer)
      REMOVE urf_valid_from_type (buffer)
      REMOVE urf_valid_from_type_codeSpace (buffer)
      REMOVE urf_enactment_fiscal_year (buffer)
      REMOVE urf_valid_to (buffer)
      REMOVE urf_valid_to_type (buffer)
      REMOVE urf_valid_to_type_codeSpace (buffer)
      REMOVE urf_expiration_fiscal_year (buffer)
      REMOVE urf_legal_grounds (buffer)
      REMOVE urf_custodian (buffer)
      REMOVE urf_notification_number (buffer)
      REMOVE urf_final_notification_date (buffer)
      REMOVE urf_final_notification_number (buffer)
      REMOVE urf_urban_plan_type (buffer)
      REMOVE urf_urban_plan_type_codeSpace (buffer)
      REMOVE urf_area_classification_type (buffer)
      REMOVE urf_area_classification_type_codeSpace (buffer)
      REMOVE urf_prefecture (buffer)
      REMOVE urf_prefecture_codeSpace (buffer)
      REMOVE urf_city (buffer)
      REMOVE urf_city_codeSpace (buffer)
      REMOVE urf_reference (buffer)
      REMOVE urf_reason (buffer)
      REMOVE urf_reason_xlink_href (buffer)
      REMOVE urf_note (buffer)
      REMOVE urf_note_xlink_href (buffer)
      REMOVE urf_survey_year (buffer)
      REMOVE citygml_level_of_detail{} (buffer)
      REMOVE urf_target{}.xlink_href (buffer)
      REMOVE urf_boundary{} (xml)
      REMOVE urf_urban_park_attribute (xml)
      REMOVE _package_path (buffer)
      REMOVE fme_geometry{0} (fme_no_geom)
      REMOVE fme_geometry{} (varchar(200))
    -> JSONTemplater_2 [ROOT]
JSONTemplater_2
    RESULT_ATTRIBUTE = attrib
    ROOT_QUERY_EXPR:
      {
          "feature_type" : fme:get-attribute("feature_type"),
          "name" : fme:get-attribute("name"),
          "function" : fme:get-attribute("function"),
          "nominalArea" : fme:get-attribute("nominalArea"),
          "location" : fme:get-attribute("location"),
          "startFrom" : fme:get-attribute("startFrom")
      }
    VISIBLE_QUERY_VALIDATE = Yes
    -> AttributeKeeper_4
AttributeKeeper_4
    CREATE_BULK_MODE_FEATURES = NO
    KEEP_ATTRS = _package,attrib
    -> 2DForcer_4
2DForcer_4
    2D -> PROJReprojector_2
PROJReprojector_2
    DEST = $(DEST_COORDSYS)
    INTERPOLATION_TYPE_NAME = Nearest Neighbor
    RASTER_CELL_SIZE = Preserve Cells
    RASTER_TOLERANCE = 0.0
    TRANSFORM_TYPE = Automatic Transformation
    REPROJECTED -> Junction_15

Bookmark: frn-ext : 都市設備（公共測量成果の精度を満たさない）柵・門・看板
Note: JSONTemplater : Output
Junction_10
    -> PythonCaller_2
fence-gate-signboard (reader OGCGEOPACKAGE_1)
    attributes: park_code text, park_name text, park_type text, facility_code text, facility_type text, facility_name text, facility_name_optional text, specific_facility_name text, quantity_numeric mediumint, quantity_unit text, size text, main_material text, main_material_optional text, installation_year smallint, disposal_limit_period mediumint, expected_usage_period mediumint, repairs_before_healthcheck_exists tinyint, repairs_before_healthcheck_year smallint, health_check_year smallint, health_check_deterioration_status text, health_check_condition text, health_check_urgency text, management_type text, expected_renewal_year_with_measures mediumint, content_2020 text, content_2021 text, content_2022 text, content_2023 text, content_2024 text, content_2025 text,
      content_2026 text, content_2027 text, content_2028 text, content_2029 text, cost_2020_thousand_yen mediumint, cost_2021_thousand_yen mediumint, cost_2022_thousand_yen mediumint, cost_2023_thousand_yen mediumint, cost_2024_thousand_yen mediumint, cost_2025_thousand_yen mediumint, cost_2026_thousand_yen mediumint, cost_2027_thousand_yen mediumint, cost_2028_thousand_yen mediumint, cost_2029_thousand_yen mediumint, note_for_longevity text, id int,PrimaryKey
    -> PythonCaller_2
PythonCaller_2
    PYTHONSOURCE:
      import fme
      import fmeobjects, json

      ATTR_TO_DICT = {
          'park_code' : 'Common_parkCode.xml',
          'park_type' : 'Common_parkType.xml',
          'facility_name' : 'Common_parkFacilityName.xml',
      }

      class CodeReplacer(object):
          def __init__(self):
              self.features = []
              self.coldelists = []

          def has_support_for(self, support_type: int):
              return support_type == fmeobjects.FME_SUPPORT_FEATURE_TABLE_SHIM

          def input(self, feature: fmeobjects.FMEFeature):
              _, missing, _ = feature.getAttributeNullMissingAndType('_codelists_json')
              if missing:
                  self.features.append(feature)
              else:
                  self.codelists = json.loads(feature.getAttribute('_codelists_json'))

          def close(self):
              for feature in self.features:
                  for attr, key in ATTR_TO_DICT.items():
                      isNull, isMissing, _ = feature.getAttributeNullMissingAndType(attr)
                      if not isNull and not isMissing:
                          d = self.codelists.get(key, {})
                          v = feature.getAttribute(attr)
                          feature.setAttribute(attr, d.get(v, v))
                  self.pyoutput(feature)

          def process_group(self):
              pass
    PYTHONSYMBOL = CodeReplacer
    -> AttributeCreator
Note: _package = frn-ext
AttributeCreator
    ATTR_TABLE = SET_TO _package (buffer) = frn-ext
    -> AttributeManager_6
    -> AttributeManager_9
AttributeManager_6
    ATTR_TABLE:
      REMOVE park_code (buffer)
      REMOVE park_name (buffer)
      REMOVE park_type (buffer)
      REMOVE facility_type (buffer)
      REMOVE facility_name (buffer)
      REMOVE facility_name_optional (buffer)
      REMOVE specific_facility_name (buffer)
      REMOVE quantity_numeric (int32)
      REMOVE quantity_unit (buffer)
      REMOVE size (buffer)
      REMOVE main_material (buffer)
      REMOVE main_material_optional (buffer)
      REMOVE installation_year (int16)
      REMOVE disposal_limit_period (int32)
      REMOVE expected_usage_period (int32)
      REMOVE repairs_before_healthcheck_exists (buffer)
      REMOVE repairs_before_healthcheck_year (int32)
      REMOVE health_check_year (int32)
      REMOVE health_check_deterioration_status (buffer)
      REMOVE health_check_condition (buffer)
      REMOVE health_check_urgency (buffer)
      REMOVE management_type (buffer)
      REMOVE expected_renewal_year_with_measures (int32)
      REMOVE content_2020 (buffer)
      REMOVE content_2021 (buffer)
      REMOVE content_2022 (buffer)
      REMOVE content_2023 (buffer)
      REMOVE content_2024 (buffer)
      REMOVE content_2025 (buffer)
      REMOVE content_2026 (buffer)
      REMOVE content_2027 (buffer)
      REMOVE content_2028 (buffer)
      REMOVE content_2029 (buffer)
      REMOVE cost_2020_thousand_yen (int32)
      REMOVE cost_2021_thousand_yen (int32)
      REMOVE cost_2022_thousand_yen (int32)
      REMOVE cost_2023_thousand_yen (int32)
      REMOVE cost_2024_thousand_yen (int32)
      REMOVE cost_2025_thousand_yen (int32)
      REMOVE cost_2026_thousand_yen (int32)
      REMOVE cost_2027_thousand_yen (int32)
      REMOVE cost_2028_thousand_yen (int32)
      REMOVE cost_2029_thousand_yen (int32)
      REMOVE note_for_longevity (buffer)
      REMOVE id (int64)
    USER_EXPOSED_ATTRIBUTES = park_code,park_name,park_type,facility_code,facility_type,facility_name,facility_name_optional,specific_facility_name,quantity_numeric,quantity_unit,size,main_material,main_material_optional,installation_year,id
    -> 2DForcer_3
AttributeManager_9
    ATTR_TABLE = REMOVE id (int64)
    -> Junction_7

Bookmark: ジオメトリを一旦FBX形式でファイル出力し、それをバイナリとして読み込み、データベースの bytea 列に格納する
Note: フィーチャーごとに別のデータセット（フォルダー）にFBXを保存しないと、再現したときに複数フィーチャー間の共通のアピアランスが欠落することがあることに注意
TempPathnameCreator
    PATHNAME_ATTR = _temp_dir
    -> FeatureWriter_FBX [LOD3]
FeatureWriter_FBX
    DATASET = @Value(_temp_dir)
    DATASET_ATTR = _dataset
    FBX_DESTINATION_DATASETTYPE_VALIDATION = Yes
    FBX_EMBED_TEXTURES = Yes
    FBX_FORMAT = 0
    FBX_LOCAL_COORDSYS_TRANSFORMATION = OFFSET_CENTROID_TO_ORIGIN
    FBX_MOVE_TO_LOCAL_COORDSYS = No
    FEATURE_TYPE_LIST_ATTR = _feature_types
    FORMAT = FBX
    GROUP_BY = _temp_dir
    MORE_SUMMARY_ATTRS = _dimension _package facility_code attrib
    TOTAL_FEATURES_WRITTEN_ATTR = _total_features_written
    SUMMARY -> FeatureReader_DataFile [INITIATOR]
FeatureReader_DataFile
    ATTRS_TO_EXPOSE = fme_basename data_file_data
    ATTR_ACCUM_MODE = Merge Initiator and Result
    ATTR_CONFLICT_RES = Use Result
    ATTR_IGNORE_NULLS = No
    COMBINE_GEOM = Use Result
    DATAFILE_DATAFILE_EXPOSE_FORMAT_ATTRS = fme_basename,char(50)
    DATAFILE_ENCODING = fme-binary
    DATAFILE_GROUP_BY_DATASET = No
    DATAFILE_READ_WHOLE_FILE_AT_ONCE = YES
    DATASET = @Value(_dataset)/@Value(_feature_types{0}.name).fbx
    FORMAT = DATAFILE
    ORDER_RESULTS = No
    OUTPUT_FEATURES_DISPLAY = Schema and Data Features
    <OTHER> -> AttributeManager_3
AttributeManager_3
    ATTR_TABLE:
      SET_TO package (buffer) = @Value(_feature_types{0}._package)
      SET_TO facility_code (buffer) = @Value(_feature_types{0}.facility_code)
      SET_TO dimension (int8) = @Value(_feature_types{0}._dimension)
      SET_TO coordsys (buffer) = $(DEST_COORDSYS)
      RENAME_SET_VALUE data_file_data > fbx_binary (binarybuffer)
      SET_TO attrib (json) = FME_CONDITIONAL:DEFAULT_VALUE'{}'BOOL_OP;OR;COMPOSITE_TEST;1;TEST _feature_types{0}.attrib ATTRIBUTE_HAS_A_VALUE _FME_BLANK_STRING_'@Value(_feature_types{0}.attrib)'FME_NUM_CONDITIONS2___
      REMOVE fme_basename (buffer)
      REMOVE _feature_types{}.count (uint64)
      REMOVE _feature_types{}.name (buffer)
      REMOVE _feature_types{}._dimension (buffer)
      REMOVE _feature_types{}._package (buffer)
      REMOVE _feature_types{}.attrib (buffer)
      REMOVE _feature_types{}.facility_code (buffer)
      REMOVE _dataset (buffer)
      REMOVE _total_features_written (uint64)
      SET_TO
    -> echigo_facility_geometry (writer POSTGRES_1)

FME custom transformer PLATEAU3.LODSplitterWithDm
DMジオメトリを抽出する機能は、CityGMLリーダーの Max Attributes Per Nested Attribute を 1 に設定してDM属性をXML要素として読み込む場合に有効となる。

Parameters:
- FME_PROCESS_GROUP_BY =   # "" Group By
- FME_PROCESS_GROUPS_ORDERED = No   # When All Features Received,No%When Group Changes (Advanced),Yes Complete Groups
- JSON_ATTRIBUTES =   # JSON Attributes
- DEST_COODSYS =   # Destination Coordinate System
- SRS_AXIS_ORDER_DISPLAY = 2,1,3   # GML SRS Axis Order for DM Geometry

Input (input)
    -> Counter
Note: DMジオメトリを抽出する機能は、CityGMLリーダーの Max Attributes Per Nested Attribute を 1 に設定してDM属性をXML要素として読み込む場合に有効
Counter
    CNT_ATTR = __temp_index
    SCOPE = Local
    START = 0
    -> PythonCaller
Note: DM属性 (XML) 抽出
PythonCaller
    NEW_ATTRIBUTES = _dm_attributes_xml
    PYTHONSOURCE:
      import fme
      import fmeobjects, re

      class DmAttributeExtractor(object):
          def __init__(self):
              pass

          def input(self, feature):
              dmAttrs = []
              for attr in feature.getAllAttributeNames():
                  if re.match(r'^uro_.+?_dm_attribute\{\d+\}$', attr):
                      dmAttrs.append(feature.getAttribute(attr))
              if dmAttrs:
                  coordSys = feature.getCoordSys()
                  dmFeature = feature.cloneAttributes()
                  dmFeature.setCoordSys(coordSys)
                  for attr in dmAttrs:
                      dmFeature.setAttribute('_dm_attributes_xml', attr)
                      self.pyoutput(dmFeature)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeExtractor
    -> TestFilter
TestFilter
    DEFAULT_VALUE = <UNFILTERED>
    PASSED_TEST_GROUP_OUTPUT = ALL
    TEST_LIST = "BOOL_OP,OR,COMPOSITE_TEST,""""""1"""""",TEST_CLAUSE,TEST _dm_attributes_xml NOT_ATTRIBUTE_HAS_A_VALUE """,All Features,"BOOL_OP,OR,COMPOSITE_TEST,""""""1"""""",TEST_CLAUSE,TEST _dm_attributes_xml ATTRIBUTE_HAS_A_VALUE """,DM Features
    All Features -> AttributeRemover
    DM Features -> CoordinateSystemExtractor
AttributeRemover
    REMOVE_ATTRS = __temp_index,_dm_attributes_xml
    -> GeometryFilter
GeometryFilter
    FILTER_MODE = COMPLETE
    FILTER_MULTI = FILTER_TYPES]Null]INSTANCES]INSTANCE]FME_CONTROLLER_QUERY_FILE]]FME_CONTROLLER_CHOICE]Complete
    Null -> Junction_10
    <UNFILTERED> -> MultipleGeometryFilter
Note: <Undefined>
Junction_10
    -> Junction_11
Note: GeometryFilter : Null
Junction_11
    -> <Undefined> (output)
MultipleGeometryFilter
    CONTAINS -> Deaggregator
    NOT_CONTAINS -> GeometryPropertyExtractor
    <REJECTED> -> GeometryPropertyExtractor
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    SPLIT_COMPOSITES = No
    DEAGGREGATED -> AttributeExposer
GeometryPropertyExtractor
    EXTRACTTYPE_PARAM = Geometry Name
    GEOM_NAME_FIELD = _geometry_name
    GQUERY:
      for $geom in //geometry
      where $geom/count(parent::geometry) = 0
      return number($geom/@fme_id)
    EXTRACTED -> AttributeExposer
    UNTOUCHED -> <Rejected> (output)
AttributeExposer
    ATTR_LIST = citygml_level_of_detail,citygml_level_of_detail{}
    -> AttributeManager
AttributeManager
    ATTR_TABLE:
      REMOVE fme_rejection_code
      SET_TO _lod = FME_CONDITIONAL:DEFAULT_VALUE'@Substring(@Value(_geometry_name),3,1)'BOOL_OP;OR;COMPOSITE_TEST;1;TEST citygml_level_of_detail ATTRIBUTE_HAS_A_VALUE _FME_BLANK_STRING_'@Value(citygml_level_of_detail)'FME_NUM_CONDITIONS2___
      REMOVE citygml_level_of_detail
      REMOVE citygml_level_of_detail{}
    -> Tester
Tester
    BOOL_OP = OR
    TEST_CLAUSE = TEST $(DEST_COODSYS) != ""
    TEST_MODE = TEST
    PASSED -> CsmapReprojector
    FAILED -> Junction_9
CsmapReprojector
    DEST = $(DEST_COODSYS)
    INTERPOLATION_TYPE_NAME = Nearest Neighbor
    RASTER_CELL_SIZE = Preserve Cells
    RASTER_TOLERANCE = 0.0
    REPROJECTED -> Junction_9
Junction_9
    -> AttributeFilter
AttributeFilter
    ATTR_NAME = _lod
    ATTR_VALUES = 0,1,2,3,4,<Missing>,<Null>,<Empty>,<Unfiltered>
    0 -> LOD0 (output)
    1 -> LOD1 (output)
    2 -> LOD2 (output)
    3 -> LOD3 (output)
    4 -> LOD4 (output)
    <MISSING> -> <Undefined> (output)
    <NULL> -> <Undefined> (output)
    <EMPTY> -> <Undefined> (output)
    <UNFILTERED> -> <Undefined> (output)
LOD0 (output)
LOD1 (output)
LOD2 (output)
LOD3 (output)
LOD4 (output)
<Undefined> (output)
<Rejected> (output)
CoordinateSystemExtractor
    CRDSYS_ATTR = _coordsys
    -> GeometryRemover
GeometryRemover
    REMOVE_COORDSYS = No
    -> XMLXQueryExtractor
XMLXQueryExtractor
    NEW_ATTRIBUTES = _dm_feature_type _geometry_name
    QUERY_EXPR:
      declare namespace uro="https://www.geospatial.jp/iur/uro/3.0";
      for $x in (//uro:lod0Geometry, //uro:lod0AnchorPoint)
      return (
          fme:set-attribute('_dm_feature_type', local-name($x/parent::node())),
          fme:set-attribute('_geometry_name', local-name($x)),
          $x
      )
    RESULT_ATTRIBUTE = __geometry
    RESULT_TYPE_NAME = Single value
    WRITE_XML_HEADER = No
    XML_ATTR = _dm_attributes_xml
    XML_REMOVE_SOURCE_ATTR = No
    XML_TYPE = Attribute specifying XML
    XQUERY_TYPE = XQuery expression
    QUERY_RESULTS -> PythonCaller_2
Note: DmGeometricAttribute, DmAnnotation 別のインデクス設定
PythonCaller_2
    GROUP_BY = __temp_index
    NEW_ATTRIBUTES = __dm_index
    PYTHONSOURCE:
      import fme
      import fmeobjects

      class DmAttributeIndexer(object):
          def __init__(self):
              self.indexG = 0 # DmGeometricAttribute
              self.indexA = 0 # DmAnnotation
              self.features = []

          def input(self, feature):
              t = feature.getAttribute('_dm_feature_type')
              if t == 'DmGeometricAttribute':
                  feature.setAttribute('__dm_index', self.indexG)
                  self.indexG += 1
              elif t == 'DmAnnotation':
                  feature.setAttribute('__dm_index', self.indexA)
                  self.indexA += 1
              self.features.append(feature)

          def process_group(self):
              for feature in self.features:
                  self.pyoutput(feature)
              self.__init__()

          def close(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeIndexer
    -> Tester_2
Tester_2
    BOOL_OP = OR
    TEST_CLAUSE = TEST @Value(__geometry) TYPE XML
    TEST_MODE = TEST
    PASSED -> GeometryReplacer
    FAILED -> AttributeManager_5
GeometryReplacer
    KIND_LONG = GML
    REMOVE_ATTRIBUTE = No
    SOURCE = @Value(__geometry)
    SRS_AXIS_ORDER_DISPLAY = $(SRS_AXIS_ORDER_DISPLAY)
    -> GeometryRefiner
GeometryRefiner
    -> 2DForcer
2DForcer
    2D -> Tester_3
Tester_3
    BOOL_OP = AND
    TEST_CLAUSE:
      TEST $(DEST_COODSYS) != ""
      TEST _coordsys ATTRIBUTE_HAS_A_VALUE ""
    TEST_MODE = TEST
    PASSED -> CsmapReprojector_2
    FAILED -> CoordinateSystemSetter
CsmapReprojector_2
    DEST = $(DEST_COODSYS)
    INTERPOLATION_TYPE_NAME = Nearest Neighbor
    RASTER_CELL_SIZE = Preserve Cells
    RASTER_TOLERANCE = 0.0
    SOURCE = @Value(_coordsys)
    REPROJECTED -> AttributeManager_2
CoordinateSystemSetter
    COORDSYS = @Value(_coordsys)
    -> AttributeManager_2
AttributeManager_2
    ATTR_TABLE:
      SET_TO _lod = 0
      REMOVE __geometry
      REMOVE _coordsys
    USER_EXPOSED_ATTRIBUTES = uro_frn_dm_attribute
    -> AttributeFilter_2
AttributeFilter_2
    ATTR_NAME = _dm_feature_type
    ATTR_VALUES = DmGeometricAttribute,DmAnnotation,<Empty>,<Missing>,<Null>,<Unfiltered>
    DmGeometricAttribute -> JSONExtractor
    DmAnnotation -> JSONExtractor_2
JSONExtractor
    EXTRACT_QUERY_TABLE = _dm_attributes_json json["uro:DmGeometricAttribute"][@Value(__dm_index)]
    JSON_DOCUMENT = $(JSON_ATTRIBUTES)
    READ_FROM_FILE = NO
    EVALUATED -> PythonCaller_3
PythonCaller_3
    NEW_ATTRIBUTES = dm_dmCode dm_dmCode_code dm_geometryType dm_geometryType_code dm_mapLevel dm_mapLevel_code dm_shapeType dm_shapeType_code
    PYTHONSOURCE:
      import fme
      import fmeobjects, json

      ATTRS = [
          'uro:dmCode',
          'uro:dmCode_code',
          'uro:geometryType',
          'uro:geometryType_code',
          'uro:mapLevel',
          'uro:mapLevel_code',
          'uro:shapeType',
          'uro:shapeType_code',
      ]

      class DmGeometricAttributeExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmGeometricAttributeExtractor
    -> AttributeManager_3
AttributeManager_3
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_3
Note: DmGeometricAttribute
Junction_3
    -> Junction_4
Junction_4
    -> DmGeometricAttribute (output)
DmGeometricAttribute (output)
JSONExtractor_2
    EXTRACT_QUERY_TABLE = _dm_attributes_json json["uro:DmAnnotation"][@Value(__dm_index)]
    JSON_DOCUMENT = $(JSON_ATTRIBUTES)
    READ_FROM_FILE = NO
    EVALUATED -> PythonCaller_4
PythonCaller_4
    NEW_ATTRIBUTES = dm_dmCode dm_dmCode_code dm_geometryType dm_geometryType_code dm_shapeType dm_shapeType_code dm_label dm_isVertical dm_size dm_orientation dm_linewidth dm_spacing
    PYTHONSOURCE:
      import fme
      import fmeobjects, json

      ATTRS = [
          'uro:dmCode',
          'uro:dmCode_code',
          'uro:geometryType',
          'uro:geometryType_code',
          'uro:shapeType',
          'uro:shapeType_code',
          'uro:label',
          'uro:isVertical',
          'uro:size',
          'uro:orientation',
          'uro:linewidth',
          'uro:spacing'
      ]

      class DmAnnotationExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAnnotationExtractor
    -> AttributeManager_4
AttributeManager_4
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_5
Note: DmAnnotation
Junction_5
    -> Junction_6
Junction_6
    -> DmAnnotation (output)
DmAnnotation (output)
AttributeManager_5
    ATTR_TABLE:
      REMOVE _geometry_name
      REMOVE __geometry
      REMOVE _coordsys
      REMOVE __temp_index
      REMOVE __dm_index
    USER_EXPOSED_ATTRIBUTES = uro_frn_dm_attribute,_dm_attribute
    -> Junction_7
Note: DmNoGeometry
Junction_7
    -> Junction_8
Junction_8
    -> DmNoGeometry (output)
DmNoGeometry (output)
