FME workspace photo_and_label_czml.fmw

Parameters:
- SourceDataset_OGCGEOPACKAGE = $(FME_MF_DIR)output\footprint.gpkg   # フットプリント GeoPackage
- SourceDataset_XLSXR = $(FME_MF_DIR)source\写真整理結果.xlsx   # 写真整理結果 (Excel)
- DestDataset_DATAFILE = $(FME_MF_DIR)output\czml   # CZML 出力先フォルダー

Readers:
- OGCGEOPACKAGE_1: OGCGEOPACKAGE from $(SourceDataset_OGCGEOPACKAGE)
- XLSXR_1: XLSXR from $(SourceDataset_XLSXR)

Writers:
- DATAFILE_1: DATAFILE to $(DestDataset_DATAFILE)

Building (reader OGCGEOPACKAGE_1)
    attributes: feature_type text, facility_code text(200), facility_name text(200), specific_facility_name text(200), facility_type text(200), installation_year smallint, expected_usage_period smallint, main_material_optional text(200), size double, management_type text(200), zmin double, zmax double, zmin_ellipsoid double, zmax_ellipsoid double, id int,PrimaryKey
    -> Counter
Bridge (reader OGCGEOPACKAGE_1)
    attributes: feature_type text, facility_code text(200), facility_name text(200), specific_facility_name text(200), facility_type text(200), installation_year smallint, expected_usage_period smallint, main_material_optional text(200), size double, management_type text(200), zmin double, zmax double, zmin_ellipsoid double, zmax_ellipsoid double, id int,PrimaryKey
    -> Counter
CityFurniture (reader OGCGEOPACKAGE_1)
    attributes: feature_type text, facility_code text(200), facility_name text(200), specific_facility_name text(200), facility_type text(200), installation_year smallint, expected_usage_period smallint, main_material_optional text(200), size double, management_type text(200), zmin double, zmax double, zmin_ellipsoid double, zmax_ellipsoid double, id int,PrimaryKey
    -> Counter
Note: label, billboard の位置: フットプリントの重心がフットプリント内にあれば重心、そうでない場合はフットプリント内の任意の点とする。
WaterBody (reader OGCGEOPACKAGE_1)
    attributes: feature_type text, facility_code text(200), facility_name text(200), specific_facility_name text(200), facility_type text(200), installation_year smallint, expected_usage_period smallint, main_material_optional text(200), size double, management_type text(200), zmin double, zmax double, zmin_ellipsoid double, zmax_ellipsoid double, id int,PrimaryKey
    -> Counter
AttributeManager
    ATTR_TABLE:
      REMOVE id (int64)
      SET_TO _zmin_leader_line (varchar(200)) = @Evaluate(@Value(zmax_ellipsoid)+0.5)
      SET_TO _zmax_leader_line (varchar(200)) = @Evaluate(@Value(_zmin_leader_line)+5)
      REMOVE zmin (real64)
      REMOVE zmax (real64)
      REMOVE zmax_ellipsoid (varchar(200))
      REMOVE _index (int64)
      REMOVE _geometry (buffer)
      REMOVE _predicate (buffer)
    -> AttributeRounder
AttributeRounder
    PLACES = 2
    ROUND_TYPE = Nearest
    SRC_ATTRS = _zmin_leader_line _zmax_leader_line
    -> AttributeRounder_2
AttributeRounder_2
    PLACES = 6
    ROUND_TYPE = Nearest
    SRC_ATTRS = _latitude _longitude
    -> VertexCreator_2
VertexCreator_2
    MEASURE_TYPE = Continuous
    MODE_NAME = Replace with Point
    XVAL = @Value(_longitude)
    YVAL = @Value(_latitude)
    ZVAL = @Value(_zmin_leader_line)
    -> VertexCreator_3
VertexCreator_3
    CLOSE_LINES = Yes
    IGNORE_DUPLICATES = No
    MEASURE_TYPE = Continuous
    MISSING_VAL_MODE = Compute
    MODE_NAME = Add Point
    XVAL = @Value(_longitude)
    YVAL = @Value(_latitude)
    ZVAL = @Value(_zmax_leader_line)
    -> CoordinateConcatenator
CoordinateConcatenator
    COORDINATES_TO_INCLUDE_DIS = X Y Z
    COORD_ATTR = _coordinates
    COORD_DELIM = ,
    ELEMENT_DELIM = ,
    -> FeatureMerger [REQUESTOR]
写真の有無 (reader XLSXR_1)
    attributes: 写真の有無 char(3), 写真データ名称 char(11), 施設コード char(7), 公園施設種類【選択】 char(15), 公園施設名【選択】 char(21), 具体的施設名称 char(63)
    -> AttributeManager_3
AttributeManager_3
    ATTR_TABLE:
      RENAME_SET_VALUE 写真の有無 > _has_photo (varchar(3))
      REMOVE 写真データ名称 (varchar(11))
      RENAME_SET_VALUE 施設コード > facility_code (varchar(7))
      REMOVE 公園施設種類【選択】 (varchar(15))
      REMOVE 公園施設名【選択】 (varchar(21))
      REMOVE 具体的施設名称 (varchar(63))
    -> Tester
Note: 写真「有」を抽出
Tester
    BOOL_OP = OR
    TEST_CLAUSE = TEST @Value(_has_photo) = 有
    TEST_MODE = TEST
    PASSED -> FeatureMerger [SUPPLIER]
FeatureMerger
    ATTR_ACCUM_MODE = Merge Supplier
    ATTR_CONFLICT_RES = Use Requestor
    IGNORE_NULLS = No
    JOIN_KEYS = @Value(facility_code) @Value(facility_code) AUTO
    MERGE_TYPE = Attributes Only
    PROCESS_DUPS = NO
    REJECT_NULL_MISSING_KEYS = No
    SUPPLIERS_FIRST = No
    MERGED -> AttributeManager_2
AttributeManager_2
    ATTR_TABLE:
      REMOVE zmin_ellipsoid (real64)
      REMOVE _zmin_leader_line (varchar(200))
      SET_TO _coordinates (real64) = [@Value(_coordinates)]
      SET_TO _text (varchar(200)) = @Value(facility_code)
        @Value(specific_facility_name)
      SET_TO _image_url (varchar(200)) = https://echigo.s3.ap-northeast-1.amazonaws.com/echigo_billboard/images/@Value(facility_code).png
    -> Counter_2
Note: facility_code / facility_name / specific_facility_name / facility_type / installation_fyear / expected_usage_period / main_material_optional / size / management_type
Counter_2
    CNT_ATTR = _packet_id
    SCOPE = Local
    START = 0
    -> JSONTemplater [ROOT]
JSONTemplater
    RESULT_ATTRIBUTE = _packet
    ROOT_QUERY_EXPR:
      {
          "id" : fme:get-attribute("_packet_id"),
          "name" : fme:get-attribute("facility_code"),
          "properties" : {|
              let $keys := (
                  'feature_type',
                  'facility_code',
                  'facility_name',
                  'specific_facility_name',
                  'facility_type',
                  'main_material_optional',
                  'management_type'
              )
              for $k in $keys
              return
              {
                  $k : {
                      "string" : fme:get-attribute($k)
                  }
              },
              let $keys := (
                  'installation_year',
                  'expected_usage_period',
                  'size'
              )
              for $k in $keys
              return
              {
                  $k : {
                      "number" : fme:get-attribute($k)
                  }
              }
          |},
          "label" : {
              "fillColor" : {
                  "rgba" : [ 0, 0, 0, 255 ]
              },
              "scale" : 1,
              "style" : "FILL",
              "text" : [ fme:get-attribute("_text") ],
              "showBackground" : true,
              "backgroundColor" : {
                  "rgba" : [ 226, 239, 218, 255 ]
              },
              "scaleByDistance" : {
                  "nearFarScalar" : [ 10, 1, 100, 0.1 ]
              }
          },
          "billboard" : {
              "image" : fme:get-attribute("_image_url"),
              "scale" : 1,
              "show" : true,
              "verticalOrigin" : "BOTTOM",
              "heightReference" : {
                  "heightReference" : "NONE"
              },
              "scaleByDistance" : {
              "nearFarScalar" : [ 10, 1, 100, 0.1 ]
              }
          },
          "position" : {
              "cartographicDegrees" : [
                  fme:get-attribute("_longitude"),
                  fme:get-attribute("_latitude"),
                  fme:get-attribute("_zmax_leader_line")
              ]
          },
          "polyline" : {
              "width" : 3,
              "material" : {
                  "solidColor" : {
                      "color" : {
                          "rgba" : [ 226, 239, 218, 255 ]
                      }
                  }
              },
              "positions" : {
                  "cartographicDegrees" : fme:get-json-attribute("_coordinates")
              }
          }
      }
    VISIBLE_QUERY_VALIDATE = Yes
    -> JSONTemplater_3 [SUB]
Creator
    GEOMTYPE = Geometry Object
    NUM = 1
    CREATED -> JSONTemplater_3 [ROOT]
JSONTemplater_3
    RESULT_ATTRIBUTE = data_file_data
    ROOT_QUERY_EXPR:
      [
          {
              "id" : "document",
              "name" : "Facility Labels",
              "version" : "1.0"
          },
          fme:process-features("SUB")
      ]
    SUB_QUERY_EXPR = fme:get-json-attribute("_packet")
    VISIBLE_QUERY_VALIDATE = Yes
    -> JSONFormatter
JSONFormatter
    ERROR_LIST_ATTR = _json_error
    FORMAT = Pretty Print
    INDENT_STYLE = Tabs
    JSON_DOCUMENT = @Value(data_file_data)
    OUTPUT_ATTR = data_file_data
    OUTPUT_ENCODING = UTF-8
    READ_FROM_FILE = NO
    REMOVE_EMPTY_OBJECTS_AND_ARRAYS = No
    REMOVE_EMPTY_STRINGS = No
    REMOVE_NULLS = No
    -> facility-labels.czml (writer DATAFILE_1)
facility-labels.czml (writer DATAFILE_1)

Bookmark: ラベル・ビルボードの中心座標取得
Counter
    CNT_ATTR = _index
    SCOPE = Local
    START = 0
    -> GeometryExtractor
    -> SpatialFilter [Filter]
GeometryExtractor
    ATTR = _geometry
    KIND_LONG = FME Binary
    REMOVE_GEOMETRY = No
    -> CenterPointReplacer
CenterPointReplacer
    POINTTYPE = CENTEROFGRAV
    POINT -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    GROUP_BY = _index
    PASS_CRITERIA = Pass Against One Filter
    PREDATTR = _predicate
    PREDICATES = INTERSECTS
    USE_BOUNDING_BOX = No
    PASSED -> CoordinateExtractor
    FAILED -> GeometryReplacer
GeometryReplacer
    KIND_LONG = FME Binary
    REMOVE_ATTRIBUTE = Yes
    SOURCE = @Value(_geometry)
    -> CenterPointReplacer_2
CenterPointReplacer_2
    POINTTYPE = INSIDE
    POINT -> CoordinateExtractor
CoordinateExtractor
    IND = 0
    MODE = Specify Coordinate
    X_ATTR = _longitude
    Y_ATTR = _latitude
    -> AttributeManager
