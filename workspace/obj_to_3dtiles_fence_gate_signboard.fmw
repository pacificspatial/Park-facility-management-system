FME workspace obj_to_3dtiles_fence_gate_signboard.fmw

Parameters:
- SourceDataset_PATH = $(FME_MF_DIR)source\15202_nagaoka-shi_city_2023_citygml_1_op\udx\frn   # INCLUDE_WEB_BROWSER 3D都市モデル udx/frn フォルダー
- FENCE_GATE_SIGN_FILEGDB = $(FME_MF_DIR_USERTYPED)source\objモデル配置用\gdb\柵・門・看板_GIS取得.gdb   # 柵・門・看板GISデータ (File Geodatabase)
- SourceDataset_XLSXR_4 = $(FME_MF_DIR_USERTYPED)source\公園施設長寿命化計画対象施設.xlsx   # 公園施設長寿命化計画対象施設 (Excel)
- SourceDataset_XLSXR_5 = $(FME_MF_DIR_USERTYPED)source\objモデル配置用\看板類型化モデルDB_送付用.xlsx   # 看板類型化モデルDB (Excel)
- SourceDataset_XLSXR = $(FME_MF_DIR_USERTYPED)source\objモデル配置用\柵・門モデル化DB_送付用.xlsx   # 柵・門モデルDB (Excel)
- SourceDataset_OBJ = ""$(FME_MF_DIR_USERTYPED)source\objモデル配置用\看板\kanbanA.obj" "$(FME_MF_DIR_USERTYPED)source\objモデル配置用\看板\kanbanB.obj" "$(FME_MF_DIR_USERTYPED)source\objモデル配置用\看板\kanbanC.obj" "$(FME_MF_DIR_USERTYPED)source\objモデル配置用\看板\kanbanD.obj" "$(FME_MF_DIR_USERTYPED)source\objモデル配置用\看板\kanbanE.obj""   # 看板・門モデル (OBJ)
- SourceDataset_GEOTIFF = $(FME_MF_DIR)source\越後丘陵公園_地形\越後丘陵公園_数値地形図モデル.tif   # DEMラスター (GeoTIFF)
- DestDataset_CESIUM3DTILES = $(FME_MF_DIR_USERTYPED)output\3d-tiles   # 3D Tiles 出力先フォルダー
- DestDataset_OGCGEOPACKAGE = $(FME_MF_DIR_USERTYPED)output\footprint.gpkg   # フットプリント出力先 GeoPackate

Readers:
- OBJ_1: OBJ from $(SourceDataset_OBJ)
- GEOTIFF_1: GEOTIFF from $(SourceDataset_GEOTIFF) in EPSG:6676
- XLSXR_1: XLSXR from $(SourceDataset_XLSXR)
- XLSXR_2: XLSXR from $(SourceDataset_XLSXR_5)
- XLSXR_3: XLSXR from $(SourceDataset_XLSXR_4)
- FILEGDB_1: FILEGDB from $(FENCE_GATE_SIGN_FILEGDB) in EPSG:6676
- PATH_1: PATH from $(SourceDataset_PATH)

Writers:
- CESIUM3DTILES_1: CESIUM3DTILES to $(DestDataset_CESIUM3DTILES)
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> StringSearcher
Note: 56380589 / 56380680 / 56380681 / 56380598 / 56380599 / 56380690 / 56380691 / 56381508 / 56381509 / 56381600 / 56381519 / 56381610
FeatureReader
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FEATURETYPES = CityFurniture
    FORMAT = CITYGML
    INTERACT = NONE
    ORDER_RESULTS = No
    OUTPUT_FEATURES_DISPLAY = Schema and Data Features
    <OTHER> -> PLATEAU3.LODSplitterWithDm
PLATEAU3.LODSplitterWithDm
    JSON_ATTRIBUTES = {}
    SRS_AXIS_ORDER_DISPLAY = 2,1,3
    DmGeometricAttribute -> AttributeExposer
AttributeExposer
    ATTR_TABLE = uro_frn_facility_attribute{0},,uro_frn_facility_type_attribute{0},
    -> Tester_2
Tester_2
    BOOL_OP = COMPOSITE
    COMPOSITE_TEST = 1 AND 2
    TEST_CLAUSE:
      TEST @Value(uro_frn_facility_attribute{0}) TYPE XML
      TEST @Value(uro_frn_facility_type_attribute{0}) TYPE XML
    TEST_MODE = TEST
    PASSED -> XMLFlattener
XMLFlattener
    ATTRIBUTE_XML = uro_frn_facility_attribute{0}
    EMBEDDED_EXPRESSIONS = ParkFacilityLongevityPlanAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> XMLFlattener_2
Note: 対象施設の条件: facilityId の先頭3文字が次のいずれか / ENR, SYU, KYU, YUG, UND, KYO, BEN, KAN, SNO
XMLFlattener_2
    ATTRIBUTE_XML = uro_frn_facility_type_attribute{0}
    EMBEDDED_EXPRESSIONS = FacilityTypeAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> AttributeExposer_2
AttributeExposer_2
    ATTR_TABLE = facilityId,,function,,specificFacilityName,,mainMaterialOptional,,size,,installationYear,,expectedUsagePeriod,,managementType,,facilityName,
    -> Tester_3
Tester_3
    BOOL_OP = OR
    TEST_CLAUSE = TEST @Left(@Value(facilityId),3) IN ENR,SYU,KYU,YUG,UND,KYO,BEN,KAN,SNO
    TEST_MODE = TEST
    PASSED -> AttributeManager
AttributeManager
    ATTR_TABLE:
      REMOVE _geometry_name (buffer)
      REMOVE _lod (varchar(200))
      REMOVE uro_frn_facility_attribute{} (xml)
      REMOVE uro_frn_facility_type_attribute{} (xml)
      REMOVE dm_feature_type (buffer)
      REMOVE dm_attributes_xml (buffer)
      REMOVE dm_attributes_json (varchar(200))
      REMOVE dm_dmCode (buffer)
      REMOVE dm_dmCode_code (buffer)
      REMOVE dm_geometryType (buffer)
      REMOVE dm_geometryType_code (buffer)
      REMOVE dm_mapLevel (buffer)
      REMOVE dm_mapLevel_code (buffer)
      REMOVE dm_shapeType (buffer)
      REMOVE dm_shapeType_code (buffer)
    USER_EXPOSED_ATTRIBUTES = mainMaterial
    -> CsmapReprojector
Note: -> EPSG:6676
CsmapReprojector
    DEST = EPSG:6676
    INTERPOLATION_TYPE_NAME = Nearest Neighbor
    RASTER_CELL_SIZE = Preserve Cells
    RASTER_TOLERANCE = 0.0
    REPROJECTED -> SchemaMapper
柵_門_看板_GIS取得 (reader FILEGDB_1)
    attributes: OBJECTID objectid, KEY text(7), Shape_Length double, KEY_1 text(8000), park_code int, park_name text(8000), park_type int, facility_id text(8000), function__ int, facility_name int, facility_name_optional text(8000), specific_facility_name text(8000), num_of_facilities_quantity int, num_of_facilities_quantity_unit int, size text(8000), main_material int, main_material_optional text(8000), installation_year int, disposal_limit_period int, expected_usage_period int, rep_bf_pk_h_assmt_repair text(8000), rep_bf_pk_h_assmt_repair_fiscal_year text(8000), pk_h_asst___assessment_fiscal_year int, pk_h_asst___deterioration_status text(8000), pk_h_asst___condition int, pk_h_asst___urgency int, management_type int, expected_renewal_year_with_measures int, lg_meas_0_fiscal_year_for_countermeasures int, lg_meas_0_cuntm_cost_cost int,
      lg_meas_0_cuntm_cost_cost_unit text(8000), lg_meas_0_description text(8000), lg_meas_1_fiscal_year_for_countermeasures int, lg_meas_1_cuntm_cost_cost int, lg_meas_1_cuntm_cost_cost_unit text(8000), lg_meas_1_description text(8000), lg_meas_2_fiscal_year_for_countermeasures int, lg_meas_2_cuntm_cost_cost int, lg_meas_2_cuntm_cost_cost_unit text(8000), lg_meas_2_description text(8000), lg_meas_3_fiscal_year_for_countermeasures int, lg_meas_3_cuntm_cost_cost int, lg_meas_3_cuntm_cost_cost_unit text(8000), lg_meas_3_description text(8000), lg_meas_4_fiscal_year_for_countermeasures int, lg_meas_4_cuntm_cost_cost int, lg_meas_4_cuntm_cost_cost_unit text(8000), lg_meas_4_description text(8000), lg_meas_5_fiscal_year_for_countermeasures int, lg_meas_5_cuntm_cost_cost int, lg_meas_5_cuntm_cost_cost_unit text(8000), lg_meas_5_description text(8000), lg_meas_6_fiscal_year_for_countermeasures int, lg_meas_6_cuntm_cost_cost int, lg_meas_6_cuntm_cost_cost_unit text(8000), lg_meas_6_description text(8000), lg_meas_7_fiscal_year_for_countermeasures int, lg_meas_7_cuntm_cost_cost int, lg_meas_7_cuntm_cost_cost_unit text(8000), lg_meas_7_description text(8000),
      lg_meas_8_fiscal_year_for_countermeasures int, lg_meas_8_cuntm_cost_cost int, lg_meas_8_cuntm_cost_cost_unit text(8000), lg_meas_8_description text(8000), lg_meas_9_fiscal_year_for_countermeasures int, lg_meas_9_cuntm_cost_cost int, lg_meas_9_cuntm_cost_cost_unit text(8000), lg_meas_9_description text(8000), note_for_longevity text(8000), Class text(255), facilityID text(8000), size_unit text(8000), f text(255)
    -> AttributeManager_7
AttributeManager_7
    ATTR_TABLE:
      RENAME_SET_VALUE facilityID > facilityId (varchar(8000))
      RENAME_SET_VALUE function__ > function (int32)
      RENAME_SET_VALUE specific_facility_name > specificFacilityName (varchar(8000))
      RENAME_SET_VALUE main_material_optional > mainMaterialOptional (varchar(8000))
      RENAME_SET_VALUE installation_year > installationYear (int32)
      RENAME_SET_VALUE expected_usage_period > expectedUsagePeriod (int32)
      RENAME_SET_VALUE management_type > managementType (int32)
      RENAME_SET_VALUE facility_name > facilityName (int32)
      REMOVE OBJECTID (int32)
      REMOVE KEY (varchar(7))
      REMOVE Shape_Length (real64)
      REMOVE KEY_1 (varchar(8000))
      REMOVE park_code (int32)
      REMOVE park_name (varchar(8000))
      REMOVE park_type (int32)
      REMOVE facility_id (varchar(8000))
      REMOVE facility_name_optional (varchar(8000))
      REMOVE num_of_facilities_quantity (int32)
      REMOVE num_of_facilities_quantity_unit (int32)
      REMOVE main_material (int32)
      REMOVE disposal_limit_period (int32)
      REMOVE rep_bf_pk_h_assmt_repair (varchar(8000))
      REMOVE rep_bf_pk_h_assmt_repair_fiscal_year (varchar(8000))
      REMOVE pk_h_asst___assessment_fiscal_year (int32)
      REMOVE pk_h_asst___deterioration_status (varchar(8000))
      REMOVE pk_h_asst___condition (int32)
      REMOVE pk_h_asst___urgency (int32)
      REMOVE expected_renewal_year_with_measures (int32)
      REMOVE lg_meas_0_fiscal_year_for_countermeasures (int32)
      REMOVE lg_meas_0_cuntm_cost_cost (int32)
      REMOVE lg_meas_0_cuntm_cost_cost_unit (varchar(8000))
      REMOVE lg_meas_0_description (varchar(8000))
      REMOVE lg_meas_1_fiscal_year_for_countermeasures (int32)
      REMOVE lg_meas_1_cuntm_cost_cost (int32)
      REMOVE lg_meas_1_cuntm_cost_cost_unit (varchar(8000))
      REMOVE lg_meas_1_description (varchar(8000))
      REMOVE lg_meas_2_fiscal_year_for_countermeasures (int32)
      REMOVE lg_meas_2_cuntm_cost_cost (int32)
      REMOVE lg_meas_2_cuntm_cost_cost_unit (varchar(8000))
      REMOVE lg_meas_2_description (varchar(8000))
      REMOVE lg_meas_3_fiscal_year_for_countermeasures (int32)
      REMOVE lg_meas_3_cuntm_cost_cost (int32)
      REMOVE lg_meas_3_cuntm_cost_cost_unit (varchar(8000))
      REMOVE lg_meas_3_description (varchar(8000))
      REMOVE lg_meas_4_fiscal_year_for_countermeasures (int32)
      REMOVE lg_meas_4_cuntm_cost_cost (int32)
      REMOVE lg_meas_4_cuntm_cost_cost_unit (varchar(8000))
      REMOVE lg_meas_4_description (varchar(8000))
      REMOVE lg_meas_5_fiscal_year_for_countermeasures (int32)
      REMOVE lg_meas_5_cuntm_cost_cost (int32)
      REMOVE lg_meas_5_cuntm_cost_cost_unit (varchar(8000))
      REMOVE lg_meas_5_description (varchar(8000))
      REMOVE lg_meas_6_fiscal_year_for_countermeasures (int32)
      REMOVE lg_meas_6_cuntm_cost_cost (int32)
      REMOVE lg_meas_6_cuntm_cost_cost_unit (varchar(8000))
      REMOVE lg_meas_6_description (varchar(8000))
      REMOVE lg_meas_7_fiscal_year_for_countermeasures (int32)
      REMOVE lg_meas_7_cuntm_cost_cost (int32)
      REMOVE lg_meas_7_cuntm_cost_cost_unit (varchar(8000))
      REMOVE lg_meas_7_description (varchar(8000))
      REMOVE lg_meas_8_fiscal_year_for_countermeasures (int32)
      REMOVE lg_meas_8_cuntm_cost_cost (int32)
      REMOVE lg_meas_8_cuntm_cost_cost_unit (varchar(8000))
      REMOVE lg_meas_8_description (varchar(8000))
      REMOVE lg_meas_9_fiscal_year_for_countermeasures (int32)
      REMOVE lg_meas_9_cuntm_cost_cost (int32)
      REMOVE lg_meas_9_cuntm_cost_cost_unit (varchar(8000))
      REMOVE lg_meas_9_description (varchar(8000))
      REMOVE note_for_longevity (varchar(8000))
      REMOVE Class (varchar(255))
      REMOVE size_unit (varchar(8000))
      REMOVE f (varchar(255))
    -> SchemaMapper
SchemaMapper
    CSV2_CASE_SENSITIVE_FIELD_NAMES = Yes
    CSV2_CHUNK_SIZE = 100000
    CSV2_DATA_START_LINE = 2
    CSV2_DELIMITER = auto
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR)resources\code_value_mapping.csv
    FORMAT = CSV2
    IDXDESTATTR = fme_feature_type
    IDXDESTCOL = ""
    IDXSOURCEATTR = fme_feature_type
    IDXSOURCECOL = ""
    MAP_ATTRS = """""" filter description
    MATCH_ATTRS = filter code
    ROW_ID_ATTR = _schemamapper_row_ids
    TABLE = code_value_mapping
    MAPPED -> AttributeKeeper
AttributeKeeper
    CREATE_BULK_MODE_FEATURES = NO
    KEEP_ATTRS = expectedUsagePeriod,facilityId,function,installationYear,mainMaterialOptional,managementType,size,specificFacilityName,facilityName
    -> Counter
Counter_2
    CNT_ATTR = _feature_index
    SCOPE = Local
    START = 0
    -> FeatureMerger [REQUESTOR]
公園施設長寿命化計画対象 (reader XLSXR_3)
    attributes: 公園コード char(3), 公園名 char(24), 公園種別 char(6), 施設コード char(7), 施設コード【旧】 char(7), 公園施設種類【選択】 char(15), 公園施設名【選択】 char(21), 公園施設名（任意） char(48), 具体的施設名称 char(63), 数量（数値） number(5,0), 数量（単位【選択】) char(3), 規模 char(11), 主要部材【選択】 char(18), 主要部材（任意） char(39), 設置年度 number(4,0), 経過年数 number(2,0), 処分制限期間など number(2,0), 使用見込み期間 number(2,0), 健全度調査以前に実施した補修の有無（有無） char(1), 健全度調査以前に実施した補修の有無（年度） char(1), 健全度調査（年度） number(4,0), 健全度調査（劣化状況） char(285), 健全度調査（健全度） char(3), 健全度調査（緊急度） char(3), 管理類型 char(6), 対策を踏まえた更新見込み年度 number(4,0), 対策費用・2020年（千円） number(5,0), 対策内容・2020年 char(21), 対策費用・2021年（千円） number(6,0), 対策内容・2021年 char(21),
      対策費用・2022年（千円） number(6,0), 対策内容・2022年 char(21), 対策費用・2023年（千円） number(6,0), 対策内容・2023年 char(21), 対策費用・2024年（千円） number(6,0), 対策内容・2024年 char(39), 対策費用・2025年（千円） number(6,0), 対策内容・2025年 char(21), 対策費用・2026年（千円） number(6,0), 対策内容・2026年 char(21), 対策費用・2027年（千円） number(6,0), 対策内容・2027年 char(21), 対策費用・2028年（千円） number(5,0), 対策内容・2028年 char(21), 対策費用・2029年（千円） number(6,0), 対策内容・2029年 char(39), 長寿命化に向けた特記事項 char(96)
    -> Tester_4
Note: 「門」を抽出
Tester_4
    BOOL_OP = OR
    TEST_CLAUSE = TEST @Value(公園施設名【選択】) = 門
    TEST_MODE = TEST
    PASSED -> AttributeManager_2
AttributeManager_2
    ATTR_TABLE:
      REMOVE 公園コード (varchar(3))
      REMOVE 公園名 (varchar(24))
      REMOVE 公園種別 (varchar(6))
      REMOVE 施設コード【旧】 (varchar(7))
      REMOVE 公園施設種類【選択】 (varchar(15))
      REMOVE 公園施設名（任意） (varchar(48))
      REMOVE 具体的施設名称 (varchar(63))
      REMOVE 数量（数値） (number(5,0))
      REMOVE 数量（単位【選択】) (varchar(3))
      REMOVE 規模 (varchar(11))
      REMOVE 主要部材【選択】 (varchar(18))
      REMOVE 主要部材（任意） (varchar(39))
      REMOVE 設置年度 (number(4,0))
      REMOVE 経過年数 (number(2,0))
      REMOVE 処分制限期間など (number(2,0))
      REMOVE 使用見込み期間 (number(2,0))
      REMOVE 健全度調査以前に実施した補修の有無（有無） (varchar(1))
      REMOVE 健全度調査以前に実施した補修の有無（年度） (varchar(1))
      REMOVE 健全度調査（年度） (number(4,0))
      REMOVE 健全度調査（劣化状況） (varchar(285))
      REMOVE 健全度調査（健全度） (varchar(3))
      REMOVE 健全度調査（緊急度） (varchar(3))
      REMOVE 管理類型 (varchar(6))
      REMOVE 対策を踏まえた更新見込み年度 (number(4,0))
      REMOVE 対策費用・2020年（千円） (number(5,0))
      REMOVE 対策内容・2020年 (varchar(21))
      REMOVE 対策費用・2021年（千円） (number(6,0))
      REMOVE 対策内容・2021年 (varchar(21))
      REMOVE 対策費用・2022年（千円） (number(6,0))
      REMOVE 対策内容・2022年 (varchar(21))
      REMOVE 対策費用・2023年（千円） (number(6,0))
      REMOVE 対策内容・2023年 (varchar(21))
      REMOVE 対策費用・2024年（千円） (number(6,0))
      REMOVE 対策内容・2024年 (varchar(39))
      REMOVE 対策費用・2025年（千円） (number(6,0))
      REMOVE 対策内容・2025年 (varchar(21))
      REMOVE 対策費用・2026年（千円） (number(6,0))
      REMOVE 対策内容・2026年 (varchar(21))
      REMOVE 対策費用・2027年（千円） (number(6,0))
      REMOVE 対策内容・2027年 (varchar(21))
      REMOVE 対策費用・2028年（千円） (number(5,0))
      REMOVE 対策内容・2028年 (varchar(21))
      REMOVE 対策費用・2029年（千円） (number(6,0))
      REMOVE 対策内容・2029年 (varchar(39))
      REMOVE 長寿命化に向けた特記事項 (varchar(96))
    -> FeatureMerger_3 [SUPPLIER]
柵・モデルDB (reader XLSXR_1)
    attributes: 施設コード char(7), 高さ（mm） number(4,0), 厚さ（mm） number(3,0)
    -> FeatureMerger [SUPPLIER]
FeatureMerger
    ATTR_ACCUM_MODE = Merge Supplier
    ATTR_CONFLICT_RES = Use Requestor
    IGNORE_NULLS = No
    JOIN_KEYS = @Value(facilityId) @Value(施設コード) AUTO
    MERGE_TYPE = Attributes Only
    PROCESS_DUPS = NO
    REJECT_NULL_MISSING_KEYS = No
    SUPPLIERS_FIRST = No
    MERGED -> FeatureMerger_3 [REQUESTOR]
    UNMERGED_REQUESTOR -> FeatureMerger_2 [REQUESTOR]
Note: 「門」とその他に分岐
FeatureMerger_3
    ATTR_ACCUM_MODE = Merge Supplier
    ATTR_CONFLICT_RES = Use Requestor
    IGNORE_NULLS = No
    JOIN_KEYS = @Value(施設コード) @Value(施設コード) AUTO
    MERGE_TYPE = Attributes Only
    PROCESS_DUPS = NO
    REJECT_NULL_MISSING_KEYS = No
    SUPPLIERS_FIRST = No
    MERGED -> AttributeManager_3
    UNMERGED_REQUESTOR -> AttributeManager_8
Note: feature_type = Gate
AttributeManager_3
    ATTR_TABLE:
      SET_TO feature_type (buffer) = Gate
      REMOVE 施設コード (varchar(7))
      SET_TO 形状パターン (buffer) = c
      REMOVE 公園施設名【選択】 (varchar(21))
      REMOVE __temp_id (int64)
    USER_EXPOSED_ATTRIBUTES = feature_type
    -> LengthCalculator
    -> Junction_3
Note: feature_type = Fence
AttributeManager_8
    ATTR_TABLE:
      SET_TO feature_type (buffer) = Fence
      REMOVE 施設コード (varchar(7))
      REMOVE __temp_id (int64)
    USER_EXPOSED_ATTRIBUTES = feature_type
    -> LineDivider [Line]
    -> Junction_3
LineDivider
    DIM = 2D
    MODE = ToApproxLength
    OUTPUT = LinesAndPoints
    VALUE = 2
    Line -> SurfaceDraper [DRAPE_FEATURES]
    Point -> SurfaceDraper [DRAPE_FEATURES]
Note: Sheet1: 看板類型化モデルDB_送付用 / [XLSXR]
Sheet1 (reader XLSXR_2)
    attributes: 施設コード char(7), 形状パターン char(1), 高さ（mm） number(4,0), 厚さ（mm） number(2,0)
    -> FeatureMerger_2 [SUPPLIER]
FeatureMerger_2
    ATTR_ACCUM_MODE = Merge Supplier
    ATTR_CONFLICT_RES = Use Requestor
    IGNORE_NULLS = No
    JOIN_KEYS = @Value(facilityId) @Value(施設コード) AUTO
    MERGE_TYPE = Attributes Only
    PROCESS_DUPS = NO
    REJECT_NULL_MISSING_KEYS = No
    SUPPLIERS_FIRST = No
    MERGED -> AttributeManager_9
Note: feature_type = Signboard
AttributeManager_9
    ATTR_TABLE:
      SET_TO feature_type (buffer) = Signboard
      REMOVE __temp_id (int64)
      REMOVE 施設コード (varchar(7))
    USER_EXPOSED_ATTRIBUTES = feature_type
    -> Junction_3
    -> VertexCounter
VertexCounter
    CNT_ATTR = _vertexcount
    -> Junction_7
Note: Tester_2 : Input
Junction_7
    -> Junction_8
Note: VertexCounter : Output
Junction_8
    -> Tester_5
Tester_5
    BOOL_OP = OR
    TEST_CLAUSE = TEST @Value(_vertexcount) = 3
    TEST_MODE = TEST
    PASSED -> CoordinateExtractor_3
    FAILED -> AttributeRemover
Junction_4
    -> AttributeRemover
AttributeRemover
    LIST_ATTRS = _indices{} _indices{}.x _indices{}.y _indices{}.z
    REMOVE_ATTRS = _vertexcount
    -> LengthCalculator
LengthCalculator
    DIM = 2
    LEN_ATTR = _width
    MULT = 1
    -> 2DVectorCalculator
2DVectorCalculator
    ATTR_EXP = _2dvectorcalculator.+
    BEG_INDEX = 0
    DIRECTION = START_TO_END
    END_INDEX = -1
    LENGTH = 1.0
    REPLACE_GEOM = No
    VX_ATTR = _vx
    VY_ATTR = _vy
    -> CenterPointReplacer
CenterPointReplacer
    POINTTYPE = CENTER
    POINT -> PointOnRasterValueExtractor [POINT]
Junction_3
    -> GeometryExtractor
GeometryExtractor
    ATTR = _geometry
    KIND_LONG = FME Binary
    REMOVE_GEOMETRY = No
    -> Snipper
Snipper
    DEAGGREGATE_INPUT = NO
    ENDLOCATIONATTR = 50
    MEASUREMENTTYPE = 2D
    SNIPMODE = Distance (Percentage)
    STARTLOCATIONATTR = 50
    -> PointOnRasterValueExtractor_2 [POINT]
GEOTIFF (reader GEOTIFF_1)
    attributes: datatype char(255)
    -> AttributeKeeper_2
AttributeKeeper_2
    CREATE_BULK_MODE_FEATURES = NO
    -> PointOnRasterValueExtractor [RASTER]
    -> Junction
    -> Junction_5
Note: PointOnRasterValueExtractor_2 : Raster
Junction_5
    -> Junction_6
Note: AttributeKeeper_2 : Output
Junction_6
    -> PointOnRasterValueExtractor_2 [RASTER]
PointOnRasterValueExtractor_2
    INTERPOLATION_TYPE_NAME = Bilinear
    POINT -> 3DForcer
3DForcer
    KEEPZVAL = No
    ZVALATTR = @Value(_band{0}.value)
    -> PROJReprojector_3
PROJReprojector_3
    DEST = EPSG:4326
    INTERPOLATION_TYPE_NAME = Nearest Neighbor
    RASTER_CELL_SIZE = Preserve Cells
    RASTER_TOLERANCE = 0.0
    SOURCE = EPSG:6676
    TRANSFORM_TYPE = Automatic Transformation
    REPROJECTED -> CsmapReprojector_3
CsmapReprojector_3
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> CoordinateExtractor_2
CoordinateExtractor_2
    IND = 0
    MODE = Specify Coordinate
    X_ATTR = cemter_longitude
    Y_ATTR = center_latitude
    Z_ATTR = zmin_ellipsoid
    -> GeometryReplacer
GeometryReplacer
    KIND_LONG = FME Binary
    REMOVE_ATTRIBUTE = Yes
    SOURCE = @Value(_geometry)
    -> PROJReprojector_2
PROJReprojector_2
    DEST = EPSG:4326
    INTERPOLATION_TYPE_NAME = Nearest Neighbor
    RASTER_CELL_SIZE = Preserve Cells
    RASTER_TOLERANCE = 0.0
    SOURCE = EPSG:6676
    TRANSFORM_TYPE = Automatic Transformation
    REPROJECTED -> Sorter_2
Sorter_2
    SORT_PARM = facilityId ALPHA ASCENDING _feature_index NUMERIC ASCENDING
    SORTED -> AttributeManager_10
AttributeManager_10
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
      RENAME_SET_VALUE 形状パターン > model_pattern (buffer)
      RENAME_SET_VALUE 高さ（mm） > height_mm (number(4,0))
      RENAME_SET_VALUE 厚さ（mm） > thickness_mm (number(3,0))
      REMOVE _feature_index (int64)
      REMOVE _band{}.value (real64)
      REMOVE _band{}.palette{}.value (real64)
    -> FenceGateSignboard (writer OGCGEOPACKAGE_1)
FenceGateSignboard (writer OGCGEOPACKAGE_1)
    attributes: feature_type text, facility_code text(200), facility_name text(200), specific_facility_name text(200), facility_type text(200), installation_year smallint, expected_usage_period smallint, main_material_optional text(200), size double, management_type text(200), model_pattern text, height_mm smallint, thickness_mm smallint, cemter_longitude double, center_latitude double, zmin_ellipsoid double
Note: SurfaceDraper : Points/Lines
Junction
    -> Junction_2
Note: AttributeKeeper_2 : Output
Junction_2
    -> SurfaceDraper [POINTS/LINES]
SurfaceDraper
    ADDZ_TYPE = Replace Z
    DRAPE_TYPE = VERTEX
    INTERPOLATION_TYPE = AUTO
    TOLERANCE = 0
    DRAPED_FEATURES -> GeometryFilter
GeometryFilter
    FILTER_MODE = SIMPLE
    FILTER_MULTI = FILTER_TYPES]"Point Line"]FME_CONTROLLER_QUERY_FILE]]FME_CONTROLLER_CHOICE]Simple
    Point -> CoordinateExtractor
    Curve -> Offsetter_2
CoordinateExtractor
    IND = 0
    MODE = Specify Coordinate
    X_ATTR = _x
    Y_ATTR = _y
    Z_ATTR = _z
    -> VertexCreator
VertexCreator
    CLOSE_LINES = Yes
    IGNORE_DUPLICATES = No
    MEASURE_TYPE = Continuous
    MISSING_VAL_MODE = Compute
    MODE_NAME = Add Point
    XVAL = @Value(_x)
    YVAL = @Value(_y)
    ZVAL = @Value(_z)+@Value(高さ（mm）)*0.001
    -> PipeReplacer
Offsetter_2
    MODE = Cartesian Coordinate
    XOFF = 0
    YOFF = 0
    ZOFF = @Value(高さ（mm）)*0.001
    OFFSET -> LineCombiner_2
LineCombiner_2
    ACCUM_ATTRS_NAME = Use Attributes From One Feature
    BREAK = no
    BREAK_CONNECTION_ATTRIBUTES = facilityId
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> PipeReplacer
PipeReplacer
    OUTER_RADIUS = @Value(厚さ（mm）)*0.001*0.5
    -> PipeEvaluator
PipeEvaluator
    PROFILE_NUM_EDGES = 16
    -> Aggregator
Aggregator
    ACCUM_ATTRS_NAME = Use Attributes From One Feature
    AGGREGATE_TYPE = Homogeneous Collection (If Possible)
    GROUP_BY = _feature_index
    MODE = Geometry - Assemble One Level
    SEP = ,
    AGGREGATE -> PROJReprojector
PointOnRasterValueExtractor
    INTERPOLATION_TYPE_NAME = Bilinear
    POINT -> AttributeManager_4
AttributeManager_4
    ATTR_TABLE:
      SET_TO _rotation_angle (varchar(200)) = @Evaluate(@radToDeg(@atan2(@Value(_vy),@Value(_vx))))
      SET_TO _x (varchar(200)) = @Evaluate(@XValue())
      SET_TO _y (varchar(200)) = @Evaluate(@YValue())
      SET_TO _z (varchar(200)) = @Value(_band{0}.value)
      REMOVE _vx (buffer)
      REMOVE _vy (buffer)
      REMOVE _band{}.value (real64)
      REMOVE _band{}.palette{}.value (real64)
    -> FeatureMerger_4 [REQUESTOR]
Note: EPSG:6676 -> EPSG:4326
PROJReprojector
    DEST = EPSG:4326
    INTERPOLATION_TYPE_NAME = Nearest Neighbor
    RASTER_CELL_SIZE = Preserve Cells
    RASTER_TOLERANCE = 0.0
    SOURCE = EPSG:6676
    TRANSFORM_TYPE = Automatic Transformation
    REPROJECTED -> CsmapReprojector_2
Note: 標高 -> 楕円体高
CsmapReprojector_2
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> Sorter
Sorter
    SORT_PARM = facilityId ALPHA ASCENDING _feature_index NUMERIC ASCENDING
    SORTED -> AttributeManager_6
AttributeManager_6
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
      RENAME_SET_VALUE 形状パターン > model_pattern (buffer)
      RENAME_SET_VALUE 高さ（mm） > height_mm (number(4,0))
      RENAME_SET_VALUE 厚さ（mm） > thickness_mm (number(3,0))
      REMOVE _width (real64)
      REMOVE _rotation_angle (varchar(200))
      REMOVE _x (varchar(200))
      REMOVE _y (varchar(200))
      REMOVE _z (varchar(200))
      REMOVE _feature_index (int64)
      REMOVE _model_pattern (varchar(200))
      REMOVE _model_width (varchar(200))
      REMOVE _model_thickness (varchar(200))
      REMOVE _model_height (varchar(200))
    -> fence-gate-signboard (writer CESIUM3DTILES_1)
fence-gate-signboard (writer CESIUM3DTILES_1)
    attributes: feature_type string, facility_code string, facility_name string, specific_facility_name string, facility_type string, installation_year int, expected_usage_period int, main_material_optional string, size float, management_type string, model_pattern string, height_mm int, thickness_mm int

Bookmark: 越後丘陵公園が含まれる図郭のファイルを抽出
StringSearcher
    CASE = no
    MATCHED_RESULT_ATTR = _meshcode
    REGEXP = ^\d+
    STRING_TO_SEARCH = @Value(path_filename)
    MATCHED -> Tester
Tester
    BOOL_OP = OR
    TEST_CLAUSE = TEST @Value(_meshcode) IN 56380589,56380680,56380681,56380598,56380599,56380690,56380691,56381508,56381509,56381600,56381519,56381610
    TEST_MODE = TEST
    PASSED -> FeatureReader [INITIATOR]

Bookmark: MultiCurve を解消
Counter
    CNT_ATTR = __temp_id
    SCOPE = Local
    START = 0
    -> LineCombiner
LineCombiner
    ACCUM_ATTRS_NAME = Use Attributes From One Feature
    BREAK = no
    BREAK_CONNECTION_ATTRIBUTES = __temp_id
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Counter_2

Bookmark: 折れ点のある看板（案内標識）ラインは、折れ点を起点とする2つのラインに分割する
CoordinateExtractor_3
    LIST_NAME = _indices
    MODE = All Coordinates
    -> VertexCreator_2
VertexCreator_2
    MEASURE_TYPE = Continuous
    MODE_NAME = Replace with Point
    XVAL = @Value(_indices{1}.x)
    YVAL = @Value(_indices{1}.y)
    -> VertexCreator_3
    -> VertexCreator_4
VertexCreator_3
    CLOSE_LINES = Yes
    IGNORE_DUPLICATES = No
    MEASURE_TYPE = Continuous
    MISSING_VAL_MODE = Compute
    MODE_NAME = Add Point
    XVAL = @Value(_indices{0}.x)
    YVAL = @Value(_indices{0}.y)
    -> Junction_4
VertexCreator_4
    CLOSE_LINES = Yes
    IGNORE_DUPLICATES = No
    MEASURE_TYPE = Continuous
    MISSING_VAL_MODE = Compute
    MODE_NAME = Add Point
    XVAL = @Value(_indices{2}.x)
    YVAL = @Value(_indices{2}.y)
    -> Junction_4

Bookmark: OBJ Model: Pattern A-E
kanbanA (reader OBJ_1)
    -> AppearanceRemover
AppearanceRemover
    SIDE_TO_REMOVE = Front and Back Sides
    -> BoundsExtractor
BoundsExtractor
    XMAX = _xmax
    XMIN = _xmin
    YMAX = _ymax
    YMIN = _ymin
    ZMAX = _zmax
    -> AttributeManager_5
AttributeManager_5
    ATTR_TABLE:
      SET_TO _model_pattern (varchar(200)) = @LowerCase(@Substring(@Value(fme_feature_type),-1,1))
      SET_TO _model_width (varchar(200)) = @Evaluate(@Value(_xmax)-@Value(_xmin))
      SET_TO _model_thickness (varchar(200)) = @Evaluate(@Value(_ymax)-@Value(_ymin))
      SET_TO _model_height (varchar(200)) = @Evaluate(@Value(_zmax))
      REMOVE fme_feature_type (buffer)
      REMOVE _xmin (real64)
      REMOVE _xmax (real64)
      REMOVE _ymin (real64)
      REMOVE _ymax (real64)
      REMOVE _zmax (real64)
    -> FeatureMerger_4 [SUPPLIER]

Bookmark: モデル形状結合、スケール、回転、位置合わせ
FeatureMerger_4
    ATTR_ACCUM_MODE = Merge Supplier
    ATTR_CONFLICT_RES = Use Requestor
    IGNORE_NULLS = No
    JOIN_KEYS = @Value(形状パターン) @Value(_model_pattern) AUTO
    MERGE_TYPE = Attributes and Geometry
    PROCESS_DUPS = NO
    REJECT_NULL_MISSING_KEYS = No
    SUPPLIERS_FIRST = No
    MERGED -> Scaler
Scaler
    RASTER_SCALING = Extents
    SCALE_ORIGIN = 0,0
    TEXT_LOC_ONLY = Location and Size
    XSCALE = @Value(_width)/@Value(_model_width)
    YSCALE = @Value(厚さ（mm）)*0.001/@Value(_model_thickness)
    ZSCALE = @Value(高さ（mm）)*0.001/@Value(_model_height)
    SCALED -> 3DRotator
3DRotator
    ANGLE = @Value(_rotation_angle)
    AXIS_CHOICE = Z Axis
    ROTATED -> Offsetter
Offsetter
    MODE = Cartesian Coordinate
    XOFF = @Value(_x)
    YOFF = @Value(_y)
    ZOFF = @Value(_z)
    OFFSET -> PROJReprojector

FME custom transformer PLATEAU3.LODSplitterWithDm
DMジオメトリを抽出する機能は、CityGMLリーダーの Max Attributes Per Nested Attribute を 1 に設定してDM属性をXML要素として読み込む場合に有効となる。

Parameters:
- FME_PROCESS_GROUP_BY =   # "" Group By
- FME_PROCESS_GROUPS_ORDERED = No   # When All Features Received,No%When Group Changes (Advanced),Yes Complete Groups
- JSON_ATTRIBUTES =   # JSON Attributes
- DEST_COODSYS =   # Destination Coordinate System
- SRS_AXIS_ORDER_DISPLAY = 2,1,3   # GML SRS Axis Order for DM Geometry

Input (input)
    -> Counter
Note: DMジオメトリを抽出する機能は、CityGMLリーダーの Max Attributes Per Nested Attribute を 1 に設定してDM属性をXML要素として読み込む場合に有効
Counter
    CNT_ATTR = __temp_index
    SCOPE = Local
    START = 0
    -> PythonCaller
Note: DM属性 (XML) 抽出
PythonCaller
    NEW_ATTRIBUTES = _dm_attributes_xml
    PYTHONSOURCE:
      import fme
      import fmeobjects, re

      class DmAttributeExtractor(object):
          def __init__(self):
              pass

          def input(self, feature):
              dmAttrs = []
              for attr in feature.getAllAttributeNames():
                  if re.match(r'^uro_.+?_dm_attribute\{\d+\}$', attr):
                      dmAttrs.append(feature.getAttribute(attr))
              if dmAttrs:
                  coordSys = feature.getCoordSys()
                  dmFeature = feature.cloneAttributes()
                  dmFeature.setCoordSys(coordSys)
                  for attr in dmAttrs:
                      dmFeature.setAttribute('_dm_attributes_xml', attr)
                      self.pyoutput(dmFeature)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeExtractor
    -> TestFilter
TestFilter
    DEFAULT_VALUE = <UNFILTERED>
    PASSED_TEST_GROUP_OUTPUT = ALL
    TEST_LIST = "BOOL_OP,OR,COMPOSITE_TEST,""""""1"""""",TEST_CLAUSE,TEST _dm_attributes_xml NOT_ATTRIBUTE_HAS_A_VALUE """,All Features,"BOOL_OP,OR,COMPOSITE_TEST,""""""1"""""",TEST_CLAUSE,TEST _dm_attributes_xml ATTRIBUTE_HAS_A_VALUE """,DM Features
    All Features -> AttributeRemover
    DM Features -> CoordinateSystemExtractor
AttributeRemover
    REMOVE_ATTRS = __temp_index,_dm_attributes_xml
    -> GeometryFilter
GeometryFilter
    FILTER_MODE = COMPLETE
    FILTER_MULTI = FILTER_TYPES]Null]INSTANCES]INSTANCE]FME_CONTROLLER_QUERY_FILE]]FME_CONTROLLER_CHOICE]Complete
    Null -> Junction_10
    <UNFILTERED> -> MultipleGeometryFilter
Note: <Undefined>
Junction_10
    -> Junction_11
Note: GeometryFilter : Null
Junction_11
    -> <Undefined> (output)
MultipleGeometryFilter
    CONTAINS -> Deaggregator
    NOT_CONTAINS -> GeometryPropertyExtractor
    <REJECTED> -> GeometryPropertyExtractor
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    SPLIT_COMPOSITES = No
    DEAGGREGATED -> AttributeExposer
GeometryPropertyExtractor
    EXTRACTTYPE_PARAM = Geometry Name
    GEOM_NAME_FIELD = _geometry_name
    GQUERY:
      for $geom in //geometry
      where $geom/count(parent::geometry) = 0
      return number($geom/@fme_id)
    EXTRACTED -> AttributeExposer
    UNTOUCHED -> <Rejected> (output)
AttributeExposer
    ATTR_LIST = citygml_level_of_detail,citygml_level_of_detail{}
    -> AttributeManager
AttributeManager
    ATTR_TABLE:
      REMOVE fme_rejection_code
      SET_TO _lod = FME_CONDITIONAL:DEFAULT_VALUE'@Substring(@Value(_geometry_name),3,1)'BOOL_OP;OR;COMPOSITE_TEST;1;TEST citygml_level_of_detail ATTRIBUTE_HAS_A_VALUE _FME_BLANK_STRING_'@Value(citygml_level_of_detail)'FME_NUM_CONDITIONS2___
      REMOVE citygml_level_of_detail
      REMOVE citygml_level_of_detail{}
    -> Tester
Tester
    BOOL_OP = OR
    TEST_CLAUSE = TEST $(DEST_COODSYS) != ""
    TEST_MODE = TEST
    PASSED -> CsmapReprojector
    FAILED -> Junction_9
CsmapReprojector
    DEST = $(DEST_COODSYS)
    INTERPOLATION_TYPE_NAME = Nearest Neighbor
    RASTER_CELL_SIZE = Preserve Cells
    RASTER_TOLERANCE = 0.0
    REPROJECTED -> Junction_9
Junction_9
    -> AttributeFilter
AttributeFilter
    ATTR_NAME = _lod
    ATTR_VALUES = 0,1,2,3,4,<Missing>,<Null>,<Empty>,<Unfiltered>
    0 -> LOD0 (output)
    1 -> LOD1 (output)
    2 -> LOD2 (output)
    3 -> LOD3 (output)
    4 -> LOD4 (output)
    <MISSING> -> <Undefined> (output)
    <NULL> -> <Undefined> (output)
    <EMPTY> -> <Undefined> (output)
    <UNFILTERED> -> <Undefined> (output)
LOD0 (output)
LOD1 (output)
LOD2 (output)
LOD3 (output)
LOD4 (output)
<Undefined> (output)
<Rejected> (output)
CoordinateSystemExtractor
    CRDSYS_ATTR = _coordsys
    -> GeometryRemover
GeometryRemover
    REMOVE_COORDSYS = No
    -> XMLXQueryExtractor
XMLXQueryExtractor
    NEW_ATTRIBUTES = _dm_feature_type _geometry_name
    QUERY_EXPR:
      declare namespace uro="https://www.geospatial.jp/iur/uro/3.0";
      for $x in (//uro:lod0Geometry, //uro:lod0AnchorPoint)
      return (
          fme:set-attribute('_dm_feature_type', local-name($x/parent::node())),
          fme:set-attribute('_geometry_name', local-name($x)),
          $x
      )
    RESULT_ATTRIBUTE = __geometry
    RESULT_TYPE_NAME = Single value
    WRITE_XML_HEADER = No
    XML_ATTR = _dm_attributes_xml
    XML_REMOVE_SOURCE_ATTR = No
    XML_TYPE = Attribute specifying XML
    XQUERY_TYPE = XQuery expression
    QUERY_RESULTS -> PythonCaller_2
Note: DmGeometricAttribute, DmAnnotation 別のインデクス設定
PythonCaller_2
    GROUP_BY = __temp_index
    NEW_ATTRIBUTES = __dm_index
    PYTHONSOURCE:
      import fme
      import fmeobjects

      class DmAttributeIndexer(object):
          def __init__(self):
              self.indexG = 0 # DmGeometricAttribute
              self.indexA = 0 # DmAnnotation
              self.features = []

          def input(self, feature):
              t = feature.getAttribute('_dm_feature_type')
              if t == 'DmGeometricAttribute':
                  feature.setAttribute('__dm_index', self.indexG)
                  self.indexG += 1
              elif t == 'DmAnnotation':
                  feature.setAttribute('__dm_index', self.indexA)
                  self.indexA += 1
              self.features.append(feature)

          def process_group(self):
              for feature in self.features:
                  self.pyoutput(feature)
              self.__init__()

          def close(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeIndexer
    -> Tester_2
Tester_2
    BOOL_OP = OR
    TEST_CLAUSE = TEST @Value(__geometry) TYPE XML
    TEST_MODE = TEST
    PASSED -> GeometryReplacer
    FAILED -> AttributeManager_5
GeometryReplacer
    KIND_LONG = GML
    REMOVE_ATTRIBUTE = No
    SOURCE = @Value(__geometry)
    SRS_AXIS_ORDER_DISPLAY = $(SRS_AXIS_ORDER_DISPLAY)
    -> GeometryRefiner
GeometryRefiner
    -> 2DForcer
2DForcer
    2D -> Tester_3
Tester_3
    BOOL_OP = AND
    TEST_CLAUSE:
      TEST $(DEST_COODSYS) != ""
      TEST _coordsys ATTRIBUTE_HAS_A_VALUE ""
    TEST_MODE = TEST
    PASSED -> CsmapReprojector_2
    FAILED -> CoordinateSystemSetter
CsmapReprojector_2
    DEST = $(DEST_COODSYS)
    INTERPOLATION_TYPE_NAME = Nearest Neighbor
    RASTER_CELL_SIZE = Preserve Cells
    RASTER_TOLERANCE = 0.0
    SOURCE = @Value(_coordsys)
    REPROJECTED -> AttributeManager_2
CoordinateSystemSetter
    COORDSYS = @Value(_coordsys)
    -> AttributeManager_2
AttributeManager_2
    ATTR_TABLE:
      SET_TO _lod = 0
      REMOVE __geometry
      REMOVE _coordsys
    USER_EXPOSED_ATTRIBUTES = uro_frn_dm_attribute
    -> AttributeFilter_2
AttributeFilter_2
    ATTR_NAME = _dm_feature_type
    ATTR_VALUES = DmGeometricAttribute,DmAnnotation,<Empty>,<Missing>,<Null>,<Unfiltered>
    DmGeometricAttribute -> JSONExtractor
    DmAnnotation -> JSONExtractor_2
JSONExtractor
    EXTRACT_QUERY_TABLE = _dm_attributes_json json["uro:DmGeometricAttribute"][@Value(__dm_index)]
    JSON_DOCUMENT = $(JSON_ATTRIBUTES)
    READ_FROM_FILE = NO
    EVALUATED -> PythonCaller_3
PythonCaller_3
    NEW_ATTRIBUTES = dm_dmCode dm_dmCode_code dm_geometryType dm_geometryType_code dm_mapLevel dm_mapLevel_code dm_shapeType dm_shapeType_code
    PYTHONSOURCE:
      import fme
      import fmeobjects, json

      ATTRS = [
          'uro:dmCode',
          'uro:dmCode_code',
          'uro:geometryType',
          'uro:geometryType_code',
          'uro:mapLevel',
          'uro:mapLevel_code',
          'uro:shapeType',
          'uro:shapeType_code',
      ]

      class DmGeometricAttributeExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmGeometricAttributeExtractor
    -> AttributeManager_3
AttributeManager_3
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_3
Note: DmGeometricAttribute
Junction_3
    -> Junction_4
Junction_4
    -> DmGeometricAttribute (output)
DmGeometricAttribute (output)
JSONExtractor_2
    EXTRACT_QUERY_TABLE = _dm_attributes_json json["uro:DmAnnotation"][@Value(__dm_index)]
    JSON_DOCUMENT = $(JSON_ATTRIBUTES)
    READ_FROM_FILE = NO
    EVALUATED -> PythonCaller_4
PythonCaller_4
    NEW_ATTRIBUTES = dm_dmCode dm_dmCode_code dm_geometryType dm_geometryType_code dm_shapeType dm_shapeType_code dm_label dm_isVertical dm_size dm_orientation dm_linewidth dm_spacing
    PYTHONSOURCE:
      import fme
      import fmeobjects, json

      ATTRS = [
          'uro:dmCode',
          'uro:dmCode_code',
          'uro:geometryType',
          'uro:geometryType_code',
          'uro:shapeType',
          'uro:shapeType_code',
          'uro:label',
          'uro:isVertical',
          'uro:size',
          'uro:orientation',
          'uro:linewidth',
          'uro:spacing'
      ]

      class DmAnnotationExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAnnotationExtractor
    -> AttributeManager_4
AttributeManager_4
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_5
Note: DmAnnotation
Junction_5
    -> Junction_6
Junction_6
    -> DmAnnotation (output)
DmAnnotation (output)
AttributeManager_5
    ATTR_TABLE:
      REMOVE _geometry_name
      REMOVE __geometry
      REMOVE _coordsys
      REMOVE __temp_index
      REMOVE __dm_index
    USER_EXPOSED_ATTRIBUTES = uro_frn_dm_attribute,_dm_attribute
    -> Junction_7
Note: DmNoGeometry
Junction_7
    -> Junction_8
Junction_8
    -> DmNoGeometry (output)
DmNoGeometry (output)

FME custom transformer LineDivider
Divides a line into multiple lines. Resulting lines and/or points which separate the lines will be output.
Every output feature will hold all the attributes of the original feature.
This transformer accepts non-aggregate Curve (Line, Arc or Path) features only.
If an input feature has other type geometry or does not have geometry, it will be output from the <Rejected> port.
Similar functions have been provided by the IterativeSnipper_2013 and the DistanceMarker_2013 in the FME Hub.
Major differences from them are:
1) Integrated their functions so that divided lines and distance markers can be created efficiently at the same time, but users still can also use each function separately. See the "Output" parameter.
2) Added "Measurement Mode" parameter so that users can choose 2D or 3D for measuring lengths.
3) Implemented with a Python script to improve performance, although the algorithm is basically same as theirs.
Parameters
Measurement Mode:
By default, the transformer measures lengths in 2D, but you can change it to 3D with this parameter setting.
Dividing Mode:
Choose one of these modes.
"Shorten to Following Length"
- snips iteratively each input line from its head by the length specified to the "Line Length or Number of Lines" parameter. Length of the final line could be less than the specified length.
"Shorten to Approximately Following Length"
- divides each input line into multiple lines having identical length which is approximately equal to the length specified to the "Line Length or Number of Lines" parameter.
"Divide to Following Number of Lines"
- divides each input line into multiple lines having identical length by the number specified to the "Line Length or Number of Lines" parameter.
Line Length or Number of Lines:
Specify a numeric value if you set "Shorten to Following Length" or "Shorten to Approximately Following Length" in the "Dividing Mode" parameter.
Specify an integer number if you set "Divide to Following Number of Lines" in the "Dividing Mode" parameter.
In both cases, the value must be greater than 0.
Output:
You can control what kind of features should be output with this parameter setting.
By default, the transformer outputs both Lines and Points, but you could run it more efficiently by selecting a preferable option if you need either only Lines or Points.
"Lines"
- outputs divided lines only. Nothing is output from the Point port.
"Lines and Points" (default)
- outputs both divided lines and points which separate the lines; including start and end nodes of the original line.
"Lines and Points except Start and End Nodes"
- outputs both divided lines and points which separate the lines; excluding start and end nodes of the original line.
"Points"
- outputs points only; including start and end nodes of the original line. Nothing is output from the Line port.
"Points except Start and End Nodes"
- outputs points only; excluding start and end nodes of the original line. Nothing is output from the Line port.

Parameters:
- DIM = 2D   # Measurement Mode
- MODE = ToLength
- VALUE =   # Line Length or Number of Lines
- OUTPUT = LinesAndPoints

Line (input)
    -> AggregateFilter
AggregateFilter
    AGGREGATE -> <Rejected> (output)
    NOT_AGGREGATE -> GeometryFilter
GeometryFilter
    BREAK_AGG = No
    GEOM_PORT_NAMES = Line Arc
    LINE -> AttributeCreator
    ARC -> AttributeCreator
    <UNFILTERED> -> <Rejected> (output)
AttributeCreator
    ATTR_LIST = __linedivider.dim,$(DIM),__linedivider.mode,$(MODE),__linedivider.value,@Evaluate($(VALUE)),__linedivider.output,$(OUTPUT)
    -> PythonCaller
PythonCaller
    HIDE_ATTRIBUTES = __linedivider.dim __linedivider.mode __linedivider.value __linedivider.output
    PYTHONSOURCE:
      # 2014-11-15, Takashi Iijima, Original Implementation
      # 2015-05-11, Takashi Iijima, Added Arc support; Fixed a problem on creating interval points of Path
      # 2017-06-26, Takashi Iijima, Updated to improve robustness.
      # 2020-01-12, Takashi Iijima, Changed Default Python Interpreter to 3.6+, saved with FME 2017.1.2.1

      import fmeobjects, math

      class LineDivider(object):
          def input(self, feature):
              is3D = (feature.getAttribute('__linedivider.dim') == '3D')
              mode = feature.getAttribute('__linedivider.mode')
              value = float(feature.getAttribute('__linedivider.value'))
              output = feature.getAttribute('__linedivider.output')
              for attr in ['dim', 'mode', 'value', 'output']:
                  feature.removeAttribute('__linedivider.' + attr)

              coordSys = feature.getCoordSys()
              outputLines = output.startswith('Lines')
              outputPoints = output.startswith('LinesAndPoints') or output.startswith('Points')
              outputEndNodes = outputPoints and not output.endswith('ExceptEndNodes')

              # Get original curve geometry
              curve = feature.getGeometry()
              length = curve.getLength(is3D)
              numLines = int(round(value) if mode == 'ToNumber' else math.ceil(length / value))
              len = value if mode == 'ToLength' else length / numLines

              for n, (beg, end) in enumerate([(i*len, (i+1)*len) for i in range(numLines)], 1):
                  # Snip the original curve
                  if n == numLines:
                      end = -1
                  curve.snip(fmeobjects.SNIP_DISTANCE, is3D, beg, end)

                  if outputLines:
                      line = feature.cloneAttributes()
                      line.setGeometry(curve)
                      line.setCoordSys(coordSys)
                      self.pyoutput(line)

                  if outputPoints and (0.0 < beg or outputEndNodes):
                      point = feature.cloneAttributes()
                      point.setGeometry(curve.getStartPoint())
                      point.setCoordSys(coordSys)
                      self.pyoutput(point)

                  # Restore original curve geometry
                  curve = feature.getGeometry()

              if outputEndNodes:
                  point = feature.cloneAttributes()
                  point.setGeometry(curve.getEndPoint())
                  point.setCoordSys(coordSys)
                  self.pyoutput(point)
    PYTHONSYMBOL = LineDivider
    -> GeometryFilter_2
GeometryFilter_2
    BREAK_AGG = No
    GEOM_PORT_NAMES = Point Line Arc
    POINT -> Point (output)
    LINE -> Line (output)
    ARC -> Line (output)
Line (output)
Point (output)
<Rejected> (output)

FME custom transformer 2DVectorCalculator
Calculates (x, y) components of a 2D vector defined by the parameter settings, and stores them as new attributes.
Optionally this transformer replaces feature geometry with a line segment representing the resulting vector.
Since it can also calculate a normal vector, may be useful to create a perpendicular line against the original geometry.
If there is one of the following conditions, the input feature will be output from the Failed port.
The reason for the failure will be stored in a new attribute named "_faiulre_reason".
- the number of coordinates is less than 2.
- specified start or end index is out of range.
- specified start index is equal to end index.
- the start and end coordinates are too close (the distance is less than 1.0e-8).
Parameters
Start Index:
Specify the index of a coordinate which should be used as start point for defining the vector.
End Index:
Specify the index of a coordinate which should be used as end point for defining the vector.
Note: The Start/End Index should be 0-based sequential number in the sequence of input geometry coordinates.
A negative index can also be used; it indicates the number that was counted from tail of the sequence.
For example, -1 indicates the last one in the sequence; -2 indicates the previous one; and so on.
Vector Direction:
Choose one of these as the direction of the vector.
-----
Start to End
Normal Left
Normal Right
End to Start
-----
Note: "Normal Left/Right" means the left/right hand side perpendicular direction against "Start to End" direction.
Vector Length:
Specify the length of the vector.
Note: If you specify a negative value to this parameter, the resulting vector direction will be reversed against the direction specified by the "Vector Direction" parameter.
X Component Attribute:
Specify the name of attribute that should store x-component of the vector.
Y Component Attribute:
Specify the name of attribute that should store y-component of the vector.
Replace Geometry:
If you choose "No" for this parameter, the original geometry will be preserved with no transformation.
If you choose "Yes", the geometry will be replaced with a line segment.
The direction and length of the line represent the resulting vector, and the start node will be located at a point specified by the "Start Index" parameter.

Parameters:
- BEG_INDEX = 0   # Start Index
- END_INDEX = -1   # End Index
- DIRECTION = START_TO_END   # Start to End,START_TO_END%Normal Left,NORMAL_LEFT%Normal Right,NORMAL_RIGHT%End to Start,END_TO_START Vector Direction
- LENGTH = 1.0   # Vector Length
- VX_ATTR = _vx   # TYPE:varchar(200) X Component Attribute
- VY_ATTR = _vy   # TYPE:varchar(200) Y Component Attribute
- REPLACE_GEOM = No   # Replace Geometry
- ATTR_EXP = _2dvectorcalculator.+   # Expression to Remove

Input (input)
    -> AttributeCreator
Note: AttributeCreator [AttributeCreator] / _2dvectorcalculator.beg_index = @Evaluate($(BEG_INDEX)) / _2dvectorcalculator.end_index = @Evaluate($(END_INDEX)) / _2dvectorcalculator.direction = $(DIRECTION) / _2dvectorcalculator.length = @Evaluate($(LENGTH)) / _2dvectorcalculator.replace_geom = $(REPLACE_GEOM)
AttributeCreator
    ATTR_LIST = _2dvectorcalculator.beg_index,@Evaluate($(BEG_INDEX)),_2dvectorcalculator.end_index,@Evaluate($(END_INDEX)),_2dvectorcalculator.direction,$(DIRECTION),_2dvectorcalculator.length,@Evaluate($(LENGTH)),_2dvectorcalculator.replace_geom,$(REPLACE_GEOM)
    -> TclCaller
TclCaller
    NEW_ATTRIBUTES = _2dvectorcalculator.vx _2dvectorcalculator.vy
    SRC:
      proc calc2DVector {} {
          set numCoords [FME_Coordinates numCoords]
          if {$numCoords < 2} {
              return "the number of coordinates is less than 2"
          }
          set beg [FME_GetAttribute "_2dvectorcalculator.beg_index"]
          if {$beg < 0} {
              set beg [expr $numCoords + $beg]
          }
          if {$beg < 0 || $numCoords <= $beg} {
              return "start index is out of range"
          }
          set end [FME_GetAttribute "_2dvectorcalculator.end_index"]
          if {$end < 0} {
              set end [expr $numCoords + $end]
          }
          if {$end < 0 || $numCoords <= $end} {
              return "end index is out of range"
          }
          if {$beg == $end} {
              return "start index is equal to end index"
          }
          set x0 [FME_Execute Coordinate x $beg FLATTEN_AGGREGATE]
          set y0 [FME_Execute Coordinate y $beg FLATTEN_AGGREGATE]
          set dx [expr [FME_Execute Coordinate x $end FLATTEN_AGGREGATE] - $x0]
          set dy [expr [FME_Execute Coordinate y $end FLATTEN_AGGREGATE] - $y0]
          set len [expr hypot($dx, $dy)]
          if {$len < 1.0e-8} {
              return "start and end coordinates are too close"
          }
          set scale [expr double([FME_GetAttribute "_2dvectorcalculator.length"]) / $len]
          set direction [FME_GetAttribute "_2dvectorcalculator.direction"]
          if {[string equal $direction START_TO_END]} {
              set vx [expr $dx * $scale]
              set vy [expr $dy * $scale]
          } elseif {[string equal $direction NORMAL_LEFT]} {
              set vx [expr -($dy) * $scale]
              set vy [expr $dx * $scale]
          } elseif {[string equal $direction NORMAL_RIGHT]} {
              set vx [expr $dy * $scale]
              set vy [expr -($dx) * $scale]
          } elseif {[string equal $direction END_TO_START]} {
              set vx [expr -($dx) * $scale]
              set vy [expr -($dy) * $scale]
          } else {
              return "Debug: Invalid Direction"
          }
          FME_SetAttribute "_2dvectorcalculator.vx" $vx
          FME_SetAttribute "_2dvectorcalculator.vy" $vy
          if {[string equal [FME_GetAttribute "_2dvectorcalculator.replace_geom"] Yes]} {
              if {[FME_Execute Dimension] == 3} {
                  set z0 [FME_Execute Coordinate z $beg FLATTEN_AGGREGATE]
                  FME_Execute RemoveGeometry
                  FME_Coordinates addCoord $x0 $y0 $z0
                  FME_Coordinates addCoord [expr $x0 + $vx] [expr $y0 + $vy] $z0
              } else {
                  FME_Execute RemoveGeometry
                  FME_Coordinates addCoord $x0 $y0
                  FME_Coordinates addCoord [expr $x0 + $vx] [expr $y0 + $vy]
              }
          }
          return 1
      }
    TCLPROG = calc2DVector
    VAL_ATTR = _2dvectorcalculator.result
    -> Tester
Tester
    BOOL_OP = OR
    TEST_CLAUSE = TEST @Value(_2dvectorcalculator.result) = 1
    TEST_MODE = Automatic
    PASSED -> BulkAttributeRenamer
    FAILED -> BulkAttributeRenamer_3
BulkAttributeRenamer
    ATTRCHOICE = Selected Attributes
    ATTRLIST = _2dvectorcalculator.vx
    PATTERN_ACTION_DISP = Regular Expression Replace
    REPLACE_PATTERN = .+
    REPLACE_STR = $(VX_ATTR)
    -> BulkAttributeRenamer_2
BulkAttributeRenamer_2
    ATTRCHOICE = Selected Attributes
    ATTRLIST = _2dvectorcalculator.vy
    PATTERN_ACTION_DISP = Regular Expression Replace
    REPLACE_PATTERN = .+
    REPLACE_STR = $(VY_ATTR)
    -> BulkAttributeRemover
BulkAttributeRemover
    ATTR_EXP = $(ATTR_EXP)
    -> Output (output)
Output (output)
BulkAttributeRenamer_3
    ATTRCHOICE = Selected Attributes
    ATTRLIST = _2dvectorcalculator.result
    PATTERN_ACTION_DISP = Regular Expression Replace
    REPLACE_PATTERN = .+
    REPLACE_STR = _failure_reason
    -> BulkAttributeRemover_2
BulkAttributeRemover_2
    ATTR_EXP = $(ATTR_EXP)
    -> Failed (output)
Failed (output)
