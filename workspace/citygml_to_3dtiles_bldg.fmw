FME workspace citygml_to_3dtiles_bldg.fmw

Parameters:
- SourceDataset_PATH = $(FME_MF_DIR)source\15202_nagaoka-shi_city_2023_citygml_1_op\udx\bldg   # INCLUDE_WEB_BROWSER 3D都市モデル udx/bldg フォルダー
- DestDataset_CESIUM3DTILES = $(FME_MF_DIR)output\3d-tiles   # 3D Tiles 出力先フォルダー
- DestDataset_OGCGEOPACKAGE = $(FME_MF_DIR)output\footprint.gpkg   # フットプリント出力先 GeoPackage

Readers:
- PATH_1: PATH from $(SourceDataset_PATH)

Writers:
- CESIUM3DTILES_1: CESIUM3DTILES to $(DestDataset_CESIUM3DTILES)
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> StringSearcher
Note: 56380589 / 56380680 / 56380681 / 56380598 / 56380599 / 56380690 / 56380691 / 56381508 / 56381509 / 56381600 / 56381519 / 56381610
FeatureReader
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FEATURETYPES = Building
    FORMAT = CITYGML
    INTERACT = NONE
    ORDER_RESULTS = No
    OUTPUT_FEATURES_DISPLAY = Schema and Data Features
    <OTHER> -> AttributeExposer
AttributeExposer
    ATTR_TABLE = uro_bldg_facility_attribute{0},,uro_bldg_facility_type_attribute{0},
    -> Tester_2
Note: 対象施設の条件: facilityId の先頭3文字が次のいずれか / ENR, SYU, KYU, YUG, UND, KYO, BEN, KAN, SNO
Tester_2
    BOOL_OP = AND
    TEST_CLAUSE:
      TEST @Value(uro_bldg_facility_attribute{0}) TYPE XML
      TEST @Value(uro_bldg_facility_type_attribute{0}) TYPE XML
    TEST_MODE = TEST
    PASSED -> XMLFlattener
AttributeKeeper
    CREATE_BULK_MODE_FEATURES = NO
    KEEP_ATTRS = expectedUsagePeriod,facilityId,function,installationYear,mainMaterialOptional,managementType,size,specificFacilityName,feature_type,facilityName
    -> CsmapReprojector
    -> Aggregator
CsmapReprojector
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> AttributeRemover
AttributeRemover
    REMOVE_ATTRS = zmax,zmin
    -> AttributeManager_4
Note: facility_code / facility_name / specific_facility_name / facility_type / installation_fyear / expected_usage_period / main_material_optional / size / management_type
AttributeManager_4
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
    -> bldg (writer CESIUM3DTILES_1)
bldg (writer CESIUM3DTILES_1)
    attributes: feature_type string, facility_code string, facility_name string, specific_facility_name string, facility_type string, installation_year int, expected_usage_period int, main_material_optional string, size float, management_type string
Aggregator
    ACCUM_ATTRS_NAME = Use Attributes From One Feature
    AGGREGATE_TYPE = Homogeneous Collection (If Possible)
    GROUP_BY = facilityId
    MODE = Geometry - Assemble One Level
    SEP = ,
    AGGREGATE -> GeometryRefiner
GeometryRefiner
    -> BoundsExtractor
BoundsExtractor
    ZMAX = zmax
    ZMIN = zmin
    -> CsmapReprojector_2
CsmapReprojector_2
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> BoundsExtractor_2
BoundsExtractor_2
    ZMAX = zmax_ellipsoid
    ZMIN = zmin_ellipsoid
    -> SurfaceFootprintReplacer
SurfaceFootprintReplacer
    OFFSET_Z = 0
    SHADOW_MODE = Overhead Shadow
    FOOTPRINT -> 2DForcer
2DForcer
    2D -> Sorter_2
Sorter_2
    SORT_PARM = facilityId ALPHA ASCENDING
    SORTED -> AttributeManager_5
AttributeManager_5
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
    -> Table1 (writer OGCGEOPACKAGE_1)
Table1 (writer OGCGEOPACKAGE_1)
    attributes: feature_type text, facility_code text(200), facility_name text, specific_facility_name text(200), facility_type text(200), installation_year smallint, expected_usage_period smallint, main_material_optional text(200), size double, management_type text, zmin double, zmax double, zmin_ellipsoid double, zmax_ellipsoid double

Bookmark: 越後丘陵公園が含まれる図郭のファイルを抽出
StringSearcher
    CASE = no
    MATCHED_RESULT_ATTR = _meshcode
    REGEXP = ^\d+
    STRING_TO_SEARCH = @Value(path_filename)
    MATCHED -> Tester
Tester
    BOOL_OP = OR
    TEST_CLAUSE = TEST @Value(_meshcode) IN 56380589,56380680,56380681,56380598,56380599,56380690,56380691,56381508,56381509,56381600,56381519,56381610
    TEST_MODE = TEST
    PASSED -> FeatureReader [INITIATOR]

Bookmark: 属性抽出
XMLFlattener
    ATTRIBUTE_XML = uro_bldg_facility_attribute{0}
    EMBEDDED_EXPRESSIONS = ParkFacilityLongevityPlanAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> XMLFlattener_2
XMLFlattener_2
    ATTRIBUTE_XML = uro_bldg_facility_type_attribute{0}
    EMBEDDED_EXPRESSIONS = FacilityTypeAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> AttributeExposer_2
AttributeExposer_2
    ATTR_TABLE = facilityId,,function,,specificFacilityName,,mainMaterialOptional,,size,,expectedUsagePeriod,buffer,facilityName,buffer,managementType,buffer,installationYear,buffer
    -> AttributeManager
AttributeManager
    ATTR_TABLE:
      SET_TO feature_type (buffer) = Building
      REMOVE uro_bldg_facility_attribute{0} (varchar(200))
      REMOVE uro_bldg_facility_type_attribute{0} (varchar(200))
      REMOVE uro_bldg_facility_attribute{} (varchar(200))
      REMOVE uro_bldg_facility_type_attribute{} (varchar(200))
    USER_EXPOSED_ATTRIBUTES = mainMaterial
    -> SchemaMapper
SchemaMapper
    CSV2_CASE_SENSITIVE_FIELD_NAMES = Yes
    CSV2_CHUNK_SIZE = 100000
    CSV2_DATA_START_LINE = 2
    CSV2_DELIMITER = auto
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR)resources\code_value_mapping.csv
    FORMAT = CSV2
    IDXDESTATTR = fme_feature_type
    IDXDESTCOL = ""
    IDXSOURCEATTR = fme_feature_type
    IDXSOURCECOL = ""
    MAP_ATTRS = """""" filter description
    MATCH_ATTRS = filter code
    ROW_ID_ATTR = _schemamapper_row_ids
    TABLE = code_value_mapping
    MAPPED -> Tester_3
Tester_3
    BOOL_OP = OR
    TEST_CLAUSE = TEST @Left(@Value(facilityId),3) IN ENR,SYU,KYU,YUG,UND,KYO,BEN,KAN,SNO
    TEST_MODE = TEST
    PASSED -> AttributeKeeper
