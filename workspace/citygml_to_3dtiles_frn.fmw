FME workspace citygml_to_3dtiles_frn.fmw

Parameters:
- SourceDataset_PATH = $(FME_MF_DIR)source\15202_nagaoka-shi_city_2023_citygml_1_op\udx\frn   # INCLUDE_WEB_BROWSER 3D都市モデル udx/frn フォルダー
- DestDataset_CESIUM3DTILES = $(FME_MF_DIR)output\3d-tiles   # 3D Tiles 出力先フォルダー
- DestDataset_OGCGEOPACKAGE = $(FME_MF_DIR)output\footprint.gpkg   # フットプリント出力先 GeoPackage

Readers:
- PATH_1: PATH from $(SourceDataset_PATH)

Writers:
- CESIUM3DTILES_1: CESIUM3DTILES to $(DestDataset_CESIUM3DTILES)
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> StringSearcher
Note: 56380589 / 56380680 / 56380681 / 56380598 / 56380599 / 56380690 / 56380691 / 56381508 / 56381509 / 56381600 / 56381519 / 56381610
FeatureReader
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FEATURETYPES = CityFurniture
    FORMAT = CITYGML
    INTERACT = NONE
    ORDER_RESULTS = No
    OUTPUT_FEATURES_DISPLAY = Schema and Data Features
    <OTHER> -> PLATEAU3.LODSplitterWithDm
PLATEAU3.LODSplitterWithDm
    JSON_ATTRIBUTES = {}
    SRS_AXIS_ORDER_DISPLAY = 2,1,3
    LOD2 -> AttributeExposer
    LOD3 -> AttributeExposer
AttributeExposer
    ATTR_TABLE = uro_frn_facility_attribute{0},,uro_frn_facility_type_attribute{0},
    -> Tester_4
Note: 対象施設の条件: facilityId の先頭3文字が次のいずれか / ENR, SYU, KYU, YUG, UND, KYO, BEN, KAN, SNO
Tester_4
    BOOL_OP = AND
    TEST_CLAUSE:
      TEST @Value(uro_frn_facility_attribute{0}) TYPE XML
      TEST @Value(uro_frn_facility_type_attribute{0}) TYPE XML
    TEST_MODE = TEST
    PASSED -> XMLFlattener
AttributeKeeper
    CREATE_BULK_MODE_FEATURES = NO
    KEEP_ATTRS = expectedUsagePeriod,facilityId,function,installationYear,mainMaterialOptional,managementType,size,specificFacilityName,feature_type,facilityName
    -> BoundsExtractor_2
BoundsExtractor_2
    ZMAX = _zmax
    ZMIN = _zmin
    -> CsmapReprojector
    -> Tester_2
Note: 遊戯施設を抽出
Tester_2
    BOOL_OP = OR
    TEST_CLAUSE = TEST @Value(function) = 遊戯施設
    TEST_MODE = TEST
    PASSED -> Junction_4
Junction_4
    -> Junction_5
Note: Tester_2 : Passed
Junction_5
    -> CsmapReprojector_2
CsmapReprojector
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> AttributeRemover
    REPROJECTED -> Tester_3
AttributeRemover
    REMOVE_ATTRS = _zmax,_zmin
    -> AttributeManager_3
AttributeManager_3
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
    -> frn (writer CESIUM3DTILES_1)
frn (writer CESIUM3DTILES_1)
    attributes: feature_type string, facility_code string, facility_name string, specific_facility_name string, facility_type string, installation_year int, expected_usage_period int, main_material_optional string, size float, management_type string
Note: 遊戯施設以外を抽出
Tester_3
    BOOL_OP = OR
    TEST_CLAUSE = TEST @Value(function) != 遊戯施設
    TEST_MODE = TEST
    PASSED -> BoundsExtractor_3
BoundsExtractor_3
    ZMAX = zmax_ellipsoid
    ZMIN = zmin_ellipsoid
    -> SurfaceFootprintReplacer_2
SurfaceFootprintReplacer_2
    OFFSET_Z = 0
    SHADOW_MODE = Overhead Shadow
    FOOTPRINT -> 2DForcer
2DForcer
    2D -> GeometryRefiner
GeometryRefiner
    -> Sorter_2
Sorter_2
    SORT_PARM = facilityId ALPHA ASCENDING
    SORTED -> AttributeManager_4
AttributeManager_4
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
      RENAME_SET_VALUE _zmin > zmin (real64)
      RENAME_SET_VALUE _zmax > zmax (real64)
      REMOVE _list{}._zmin (real64)
      REMOVE _list{}._zmax (real64)
      REMOVE _zmin.min (real64)
      REMOVE __unused (real64)
      REMOVE _zmax.max (real64)
    -> Table1 (writer OGCGEOPACKAGE_1)
Table1 (writer OGCGEOPACKAGE_1)
    attributes: feature_type text, facility_code text(200), facility_name text(200), specific_facility_name text(200), facility_type text(200), installation_year smallint, expected_usage_period smallint, main_material_optional text(200), size double, management_type text(200), zmin double, zmax double, zmin_ellipsoid double, zmax_ellipsoid double

Bookmark: 越後丘陵公園が含まれる図郭のファイルを抽出
StringSearcher
    CASE = no
    MATCHED_RESULT_ATTR = _meshcode
    REGEXP = ^\d+
    STRING_TO_SEARCH = @Value(path_filename)
    MATCHED -> Tester
Tester
    BOOL_OP = OR
    TEST_CLAUSE = TEST @Value(_meshcode) IN 56380589,56380680,56380681,56380598,56380599,56380690,56380691,56381508,56381509,56381600,56381519,56381610
    TEST_MODE = TEST
    PASSED -> FeatureReader [INITIATOR]

Bookmark: 属性抽出
XMLFlattener
    ATTRIBUTE_XML = uro_frn_facility_attribute{0}
    EMBEDDED_EXPRESSIONS = ParkFacilityLongevityPlanAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> XMLFlattener_2
XMLFlattener_2
    ATTRIBUTE_XML = uro_frn_facility_type_attribute{0}
    EMBEDDED_EXPRESSIONS = FacilityTypeAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> AttributeExposer_2
AttributeExposer_2
    ATTR_TABLE = facilityId,,function,,specificFacilityName,,mainMaterialOptional,,size,,installationYear,,expectedUsagePeriod,,managementType,,facilityName,
    -> AttributeManager
AttributeManager
    ATTR_TABLE:
      SET_TO feature_type (buffer) = CityFurniture
      REMOVE _geometry_name (buffer)
      REMOVE _lod (varchar(200))
      REMOVE uro_frn_facility_attribute{} (xml)
      REMOVE uro_frn_facility_type_attribute{} (xml)
      SET_TO
    USER_EXPOSED_ATTRIBUTES = mainMaterial
    -> SchemaMapper
SchemaMapper
    CSV2_CASE_SENSITIVE_FIELD_NAMES = Yes
    CSV2_CHUNK_SIZE = 100000
    CSV2_DATA_START_LINE = 2
    CSV2_DELIMITER = auto
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR)resources\code_value_mapping.csv
    FORMAT = CSV2
    IDXDESTATTR = fme_feature_type
    IDXDESTCOL = ""
    IDXSOURCEATTR = fme_feature_type
    IDXSOURCECOL = ""
    MAP_ATTRS = """""" filter description
    MATCH_ATTRS = filter code
    ROW_ID_ATTR = _schemamapper_row_ids
    TABLE = code_value_mapping
    MAPPED -> Tester_5
Tester_5
    BOOL_OP = OR
    TEST_CLAUSE = TEST @Left(@Value(facilityId),3) IN ENR,SYU,KYU,YUG,UND,KYO,BEN,KAN,SNO
    TEST_MODE = TEST
    PASSED -> AttributeKeeper

Bookmark: 遊戯施設のフットプリント用立体作成
CsmapReprojector_2
    DEST = EPSG:6676
    INTERPOLATION_TYPE_NAME = Nearest Neighbor
    RASTER_CELL_SIZE = Preserve Cells
    RASTER_TOLERANCE = 0.0
    SOURCE = EPSG:6668
    REPROJECTED -> Sorter
Sorter
    SORT_PARM = facilityId ALPHA ASCENDING
    SORTED -> SurfaceFootprintReplacer
SurfaceFootprintReplacer
    OFFSET_Z = 0
    SHADOW_MODE = Overhead Shadow
    FOOTPRINT -> Bufferer
    <REJECTED> -> Junction_2
Bufferer
    ANGLE = 22.5
    CAP_STYLE = Arc
    CORNER_STYLE = Arc
    GROUP_BY = facilityId
    LIST_ATTRS_TO_INCLUDE = _zmax _zmin
    LIST_NAME = _list
    MODE = AREA
    OFFSET = 2
    OFFSET_UNITS = NONE
    PRECISION = APPROX
    BUFFERED -> Bufferer_2
Bufferer_2
    ANGLE = 22.5
    CAP_STYLE = Arc
    CORNER_STYLE = Arc
    MODE = AREA
    OFFSET = -1.7
    OFFSET_UNITS = NONE
    PRECISION = APPROX
    BUFFERED -> ListRangeExtractor
ListRangeExtractor
    MAX = __unused
    MIN = _zmin.min
    SRC_LIST = _list{}._zmin
    -> ListRangeExtractor_2
ListRangeExtractor_2
    MAX = _zmax.max
    MIN = __unused
    SRC_LIST = _list{}._zmax
    -> DonutHoleExtractor
DonutHoleExtractor
    DEAGGREGATE_INPUT = Yes
    OUTERSHELL -> Generalizer
    <REJECTED> -> Junction_3
Generalizer
    ALG_TEXT = Thin (Generalize)
    TOLERANCE = 0.1
    -> 3DForcer
3DForcer
    KEEPZVAL = No
    ZVALATTR = @Value(_zmin.min)
    -> Extruder
Extruder
    DIRECTION = Vertical
    DISTANCE = @Value(_zmax.max)-@Value(_zmin.min)
    EXTRUDED -> Aggregator
Aggregator
    ACCUM_ATTRS_NAME = Use Attributes From One Feature
    AGGREGATE_TYPE = Homogeneous Collection (If Possible)
    GROUP_BY = facilityId
    MODE = Geometry - Assemble One Level
    SEP = ,
    AGGREGATE -> PROJReprojector
PROJReprojector
    DEST = EPSG:4326
    INTERPOLATION_TYPE_NAME = Nearest Neighbor
    RASTER_CELL_SIZE = Preserve Cells
    RASTER_TOLERANCE = 0.0
    TRANSFORM_TYPE = Automatic Transformation
    REPROJECTED -> CsmapReprojector_3
CsmapReprojector_3
    DEST = EPSG:4326
    GEOID_HEIGHT_GRID = $(FME_MF_DIR)resources\gsigeo2011\gsigeo2011_ver2_2.gdc
    INTERPOLATION_TYPE_NAME = Nearest Neighbor
    RASTER_CELL_SIZE = Preserve Cells
    RASTER_TOLERANCE = 0.0
    SOURCE = EPSG:4326
    VERTICAL_HANDLING = Orthometric height -> Geocentric or ellipsoid height
    REPROJECTED -> BoundsExtractor_3
Junction_3
Junction_2

FME custom transformer PLATEAU3.LODSplitterWithDm
DMジオメトリを抽出する機能は、CityGMLリーダーの Max Attributes Per Nested Attribute を 1 に設定してDM属性をXML要素として読み込む場合に有効となる。

Parameters:
- FME_PROCESS_GROUP_BY =   # "" Group By
- FME_PROCESS_GROUPS_ORDERED = No   # When All Features Received,No%When Group Changes (Advanced),Yes Complete Groups
- JSON_ATTRIBUTES =   # JSON Attributes
- DEST_COODSYS =   # Destination Coordinate System
- SRS_AXIS_ORDER_DISPLAY = 2,1,3   # GML SRS Axis Order for DM Geometry

Input (input)
    -> Counter
Note: DMジオメトリを抽出する機能は、CityGMLリーダーの Max Attributes Per Nested Attribute を 1 に設定してDM属性をXML要素として読み込む場合に有効
Counter
    CNT_ATTR = __temp_index
    SCOPE = Local
    START = 0
    -> PythonCaller
Note: DM属性 (XML) 抽出
PythonCaller
    NEW_ATTRIBUTES = _dm_attributes_xml
    PYTHONSOURCE:
      import fme
      import fmeobjects, re

      class DmAttributeExtractor(object):
          def __init__(self):
              pass

          def input(self, feature):
              dmAttrs = []
              for attr in feature.getAllAttributeNames():
                  if re.match(r'^uro_.+?_dm_attribute\{\d+\}$', attr):
                      dmAttrs.append(feature.getAttribute(attr))
              if dmAttrs:
                  coordSys = feature.getCoordSys()
                  dmFeature = feature.cloneAttributes()
                  dmFeature.setCoordSys(coordSys)
                  for attr in dmAttrs:
                      dmFeature.setAttribute('_dm_attributes_xml', attr)
                      self.pyoutput(dmFeature)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeExtractor
    -> TestFilter
TestFilter
    DEFAULT_VALUE = <UNFILTERED>
    PASSED_TEST_GROUP_OUTPUT = ALL
    TEST_LIST = "BOOL_OP,OR,COMPOSITE_TEST,""""""1"""""",TEST_CLAUSE,TEST _dm_attributes_xml NOT_ATTRIBUTE_HAS_A_VALUE """,All Features,"BOOL_OP,OR,COMPOSITE_TEST,""""""1"""""",TEST_CLAUSE,TEST _dm_attributes_xml ATTRIBUTE_HAS_A_VALUE """,DM Features
    All Features -> AttributeRemover
    DM Features -> CoordinateSystemExtractor
AttributeRemover
    REMOVE_ATTRS = __temp_index,_dm_attributes_xml
    -> GeometryFilter
GeometryFilter
    FILTER_MODE = COMPLETE
    FILTER_MULTI = FILTER_TYPES]Null]INSTANCES]INSTANCE]FME_CONTROLLER_QUERY_FILE]]FME_CONTROLLER_CHOICE]Complete
    Null -> Junction_10
    <UNFILTERED> -> MultipleGeometryFilter
Note: <Undefined>
Junction_10
    -> Junction_11
Note: GeometryFilter : Null
Junction_11
    -> <Undefined> (output)
MultipleGeometryFilter
    CONTAINS -> Deaggregator
    NOT_CONTAINS -> GeometryPropertyExtractor
    <REJECTED> -> GeometryPropertyExtractor
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    SPLIT_COMPOSITES = No
    DEAGGREGATED -> AttributeExposer
GeometryPropertyExtractor
    EXTRACTTYPE_PARAM = Geometry Name
    GEOM_NAME_FIELD = _geometry_name
    GQUERY:
      for $geom in //geometry
      where $geom/count(parent::geometry) = 0
      return number($geom/@fme_id)
    EXTRACTED -> AttributeExposer
    UNTOUCHED -> <Rejected> (output)
AttributeExposer
    ATTR_LIST = citygml_level_of_detail,citygml_level_of_detail{}
    -> AttributeManager
AttributeManager
    ATTR_TABLE:
      REMOVE fme_rejection_code
      SET_TO _lod = FME_CONDITIONAL:DEFAULT_VALUE'@Substring(@Value(_geometry_name),3,1)'BOOL_OP;OR;COMPOSITE_TEST;1;TEST citygml_level_of_detail ATTRIBUTE_HAS_A_VALUE _FME_BLANK_STRING_'@Value(citygml_level_of_detail)'FME_NUM_CONDITIONS2___
      REMOVE citygml_level_of_detail
      REMOVE citygml_level_of_detail{}
    -> Tester
Tester
    BOOL_OP = OR
    TEST_CLAUSE = TEST $(DEST_COODSYS) != ""
    TEST_MODE = TEST
    PASSED -> CsmapReprojector
    FAILED -> Junction_9
CsmapReprojector
    DEST = $(DEST_COODSYS)
    INTERPOLATION_TYPE_NAME = Nearest Neighbor
    RASTER_CELL_SIZE = Preserve Cells
    RASTER_TOLERANCE = 0.0
    REPROJECTED -> Junction_9
Junction_9
    -> AttributeFilter
AttributeFilter
    ATTR_NAME = _lod
    ATTR_VALUES = 0,1,2,3,4,<Missing>,<Null>,<Empty>,<Unfiltered>
    0 -> LOD0 (output)
    1 -> LOD1 (output)
    2 -> LOD2 (output)
    3 -> LOD3 (output)
    4 -> LOD4 (output)
    <MISSING> -> <Undefined> (output)
    <NULL> -> <Undefined> (output)
    <EMPTY> -> <Undefined> (output)
    <UNFILTERED> -> <Undefined> (output)
LOD0 (output)
LOD1 (output)
LOD2 (output)
LOD3 (output)
LOD4 (output)
<Undefined> (output)
<Rejected> (output)
CoordinateSystemExtractor
    CRDSYS_ATTR = _coordsys
    -> GeometryRemover
GeometryRemover
    REMOVE_COORDSYS = No
    -> XMLXQueryExtractor
XMLXQueryExtractor
    NEW_ATTRIBUTES = _dm_feature_type _geometry_name
    QUERY_EXPR:
      declare namespace uro="https://www.geospatial.jp/iur/uro/3.0";
      for $x in (//uro:lod0Geometry, //uro:lod0AnchorPoint)
      return (
          fme:set-attribute('_dm_feature_type', local-name($x/parent::node())),
          fme:set-attribute('_geometry_name', local-name($x)),
          $x
      )
    RESULT_ATTRIBUTE = __geometry
    RESULT_TYPE_NAME = Single value
    WRITE_XML_HEADER = No
    XML_ATTR = _dm_attributes_xml
    XML_REMOVE_SOURCE_ATTR = No
    XML_TYPE = Attribute specifying XML
    XQUERY_TYPE = XQuery expression
    QUERY_RESULTS -> PythonCaller_2
Note: DmGeometricAttribute, DmAnnotation 別のインデクス設定
PythonCaller_2
    GROUP_BY = __temp_index
    NEW_ATTRIBUTES = __dm_index
    PYTHONSOURCE:
      import fme
      import fmeobjects

      class DmAttributeIndexer(object):
          def __init__(self):
              self.indexG = 0 # DmGeometricAttribute
              self.indexA = 0 # DmAnnotation
              self.features = []

          def input(self, feature):
              t = feature.getAttribute('_dm_feature_type')
              if t == 'DmGeometricAttribute':
                  feature.setAttribute('__dm_index', self.indexG)
                  self.indexG += 1
              elif t == 'DmAnnotation':
                  feature.setAttribute('__dm_index', self.indexA)
                  self.indexA += 1
              self.features.append(feature)

          def process_group(self):
              for feature in self.features:
                  self.pyoutput(feature)
              self.__init__()

          def close(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAttributeIndexer
    -> Tester_2
Tester_2
    BOOL_OP = OR
    TEST_CLAUSE = TEST @Value(__geometry) TYPE XML
    TEST_MODE = TEST
    PASSED -> GeometryReplacer
    FAILED -> AttributeManager_5
GeometryReplacer
    KIND_LONG = GML
    REMOVE_ATTRIBUTE = No
    SOURCE = @Value(__geometry)
    SRS_AXIS_ORDER_DISPLAY = $(SRS_AXIS_ORDER_DISPLAY)
    -> GeometryRefiner
GeometryRefiner
    -> 2DForcer
2DForcer
    2D -> Tester_3
Tester_3
    BOOL_OP = AND
    TEST_CLAUSE:
      TEST $(DEST_COODSYS) != ""
      TEST _coordsys ATTRIBUTE_HAS_A_VALUE ""
    TEST_MODE = TEST
    PASSED -> CsmapReprojector_2
    FAILED -> CoordinateSystemSetter
CsmapReprojector_2
    DEST = $(DEST_COODSYS)
    INTERPOLATION_TYPE_NAME = Nearest Neighbor
    RASTER_CELL_SIZE = Preserve Cells
    RASTER_TOLERANCE = 0.0
    SOURCE = @Value(_coordsys)
    REPROJECTED -> AttributeManager_2
CoordinateSystemSetter
    COORDSYS = @Value(_coordsys)
    -> AttributeManager_2
AttributeManager_2
    ATTR_TABLE:
      SET_TO _lod = 0
      REMOVE __geometry
      REMOVE _coordsys
    USER_EXPOSED_ATTRIBUTES = uro_frn_dm_attribute
    -> AttributeFilter_2
AttributeFilter_2
    ATTR_NAME = _dm_feature_type
    ATTR_VALUES = DmGeometricAttribute,DmAnnotation,<Empty>,<Missing>,<Null>,<Unfiltered>
    DmGeometricAttribute -> JSONExtractor
    DmAnnotation -> JSONExtractor_2
JSONExtractor
    EXTRACT_QUERY_TABLE = _dm_attributes_json json["uro:DmGeometricAttribute"][@Value(__dm_index)]
    JSON_DOCUMENT = $(JSON_ATTRIBUTES)
    READ_FROM_FILE = NO
    EVALUATED -> PythonCaller_3
PythonCaller_3
    NEW_ATTRIBUTES = dm_dmCode dm_dmCode_code dm_geometryType dm_geometryType_code dm_mapLevel dm_mapLevel_code dm_shapeType dm_shapeType_code
    PYTHONSOURCE:
      import fme
      import fmeobjects, json

      ATTRS = [
          'uro:dmCode',
          'uro:dmCode_code',
          'uro:geometryType',
          'uro:geometryType_code',
          'uro:mapLevel',
          'uro:mapLevel_code',
          'uro:shapeType',
          'uro:shapeType_code',
      ]

      class DmGeometricAttributeExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmGeometricAttributeExtractor
    -> AttributeManager_3
AttributeManager_3
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_3
Note: DmGeometricAttribute
Junction_3
    -> Junction_4
Junction_4
    -> DmGeometricAttribute (output)
DmGeometricAttribute (output)
JSONExtractor_2
    EXTRACT_QUERY_TABLE = _dm_attributes_json json["uro:DmAnnotation"][@Value(__dm_index)]
    JSON_DOCUMENT = $(JSON_ATTRIBUTES)
    READ_FROM_FILE = NO
    EVALUATED -> PythonCaller_4
PythonCaller_4
    NEW_ATTRIBUTES = dm_dmCode dm_dmCode_code dm_geometryType dm_geometryType_code dm_shapeType dm_shapeType_code dm_label dm_isVertical dm_size dm_orientation dm_linewidth dm_spacing
    PYTHONSOURCE:
      import fme
      import fmeobjects, json

      ATTRS = [
          'uro:dmCode',
          'uro:dmCode_code',
          'uro:geometryType',
          'uro:geometryType_code',
          'uro:shapeType',
          'uro:shapeType_code',
          'uro:label',
          'uro:isVertical',
          'uro:size',
          'uro:orientation',
          'uro:linewidth',
          'uro:spacing'
      ]

      class DmAnnotationExtractor(object):
          def __init__(self):
              pass

          def input(self, feature):
              d = feature.getAttribute('_dm_attributes_json')
              if d:
                  attrib = {}
                  d = json.loads(d)
                  for attr in ATTRS:
                      attrib[attr] = d.get(attr, None)
                  for attr, value in attrib.items():
                      if value != None:
                          feature.setAttribute(attr.replace('uro:', 'dm_'), value)

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = DmAnnotationExtractor
    -> AttributeManager_4
AttributeManager_4
    ATTR_TABLE:
      RENAME_SET_VALUE _dm_feature_type > dm_feature_type
      RENAME_SET_VALUE _dm_attributes_xml > dm_attributes_xml
      RENAME_SET_VALUE _dm_attributes_json > dm_attributes_json
      REMOVE __temp_index
      REMOVE __dm_index
    -> Junction_5
Note: DmAnnotation
Junction_5
    -> Junction_6
Junction_6
    -> DmAnnotation (output)
DmAnnotation (output)
AttributeManager_5
    ATTR_TABLE:
      REMOVE _geometry_name
      REMOVE __geometry
      REMOVE _coordsys
      REMOVE __temp_index
      REMOVE __dm_index
    USER_EXPOSED_ATTRIBUTES = uro_frn_dm_attribute,_dm_attribute
    -> Junction_7
Note: DmNoGeometry
Junction_7
    -> Junction_8
Junction_8
    -> DmNoGeometry (output)
DmNoGeometry (output)
