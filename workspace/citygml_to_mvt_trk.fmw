FME workspace citygml_to_mvt_trk.fmw

Parameters:
- SourceDataset_PATH = $(FME_MF_DIR)source\15202_nagaoka-shi_city_2023_citygml_1_op\udx\trk   # INCLUDE_WEB_BROWSER 3D都市モデル udx/trk フォルダー
- DestDataset_MVT_TILESET = $(FME_MF_DIR)output\mvt\trk   # MVT 出力先フォルダー
- DestDataset_OGCGEOPACKAGE = $(FME_MF_DIR)output\footprint.gpkg   # フットプリント出力先 GeoPackage

Readers:
- PATH_1: PATH from $(SourceDataset_PATH)

Writers:
- MVT_TILESET_1: MVT_TILESET to $(DestDataset_MVT_TILESET)
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> StringSearcher
Note: 56380589 / 56380680 / 56380681 / 56380598 / 56380599 / 56380690 / 56380691 / 56381508 / 56381509 / 56381600 / 56381519 / 56381610
FeatureReader
    ATTRS_TO_EXPOSE = gml_id gml_parent_id
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FORMAT = CITYGML
    INTERACT = NONE
    ORDER_RESULTS = No
    OUTPUT_FEATURES_DISPLAY = Schema and Data Features
    <OTHER> -> FeatureTypeFilter
FeatureTypeFilter
    ATTRIBUTES = TrafficArea,AuxiliaryTrafficArea,Track,<Blank>,<Unfiltered>
    TrafficArea -> Junction
    AuxiliaryTrafficArea -> Junction
    Track -> AttributeExposer
Junction
    -> Junction_2
Note: FeatureMerger : Requestor
Junction_2
    -> Junction_3
Note: Junction : Output
Junction_3
    -> FeatureMerger [REQUESTOR]
AttributeExposer
    ATTR_TABLE = uro_tran_facility_attribute{0},,uro_tran_facility_type_attribute{0},
    -> Tester_2
Note: 対象施設の条件: facilityId の先頭3文字が次のいずれか / ENR, SYU, KYU, YUG, UND, KYO, BEN, KAN, SNO
Tester_2
    BOOL_OP = AND
    TEST_CLAUSE:
      TEST @Value(uro_tran_facility_attribute{0}) TYPE XML
      TEST @Value(uro_tran_facility_type_attribute{0}) TYPE XML
    TEST_MODE = TEST
    PASSED -> XMLFlattener
FeatureMerger
    ATTR_ACCUM_MODE = Merge Supplier
    ATTR_CONFLICT_RES = Use Requestor
    IGNORE_NULLS = No
    JOIN_KEYS = @Value(gml_parent_id) @Value(gml_id) AUTO
    MERGE_TYPE = Attributes Only
    PROCESS_DUPS = NO
    REJECT_NULL_MISSING_KEYS = No
    SUPPLIERS_FIRST = No
    MERGED -> AttributeManager_4
AttributeManager_4
    ATTR_TABLE:
      RENAME_SET_VALUE facilityId > facility_code (varchar(200))
      RENAME_SET_VALUE facilityName > facility_name (varchar(200))
      RENAME_SET_VALUE specificFacilityName > specific_facility_name (varchar(200))
      RENAME_SET_VALUE function > facility_type (varchar(200))
      RENAME_SET_VALUE installationYear > installation_year (int16)
      RENAME_SET_VALUE expectedUsagePeriod > expected_usage_period (int16)
      RENAME_SET_VALUE mainMaterialOptional > main_material_optional (varchar(200))
      RENAME_SET_VALUE managementType > management_type (varchar(200))
      REMOVE gml_id (buffer)
      REMOVE _schemamapper_row_ids (buffer)
    -> 2DForcer
2DForcer
    2D -> CoordinateSystemSetter
CoordinateSystemSetter
    COORDSYS = EPSG:4326
    -> trk (writer MVT_TILESET_1)
    -> Track (writer OGCGEOPACKAGE_1)
trk (writer MVT_TILESET_1)
    attributes: facility_code string, facility_name string, specific_facility_name string, facility_type string, installation_year int64, expected_usage_period int64, main_material_optional string, size double, management_type string, gml_parent_id string
Track (writer OGCGEOPACKAGE_1)
    attributes: facility_code text, facility_name text, specific_facility_name text, facility_type text, installation_year smallint, expected_usage_period smallint, main_material_optional text, size double, management_type text

Bookmark: 越後丘陵公園が含まれる図郭のファイルを抽出
StringSearcher
    CASE = no
    MATCHED_RESULT_ATTR = _meshcode
    REGEXP = ^\d+
    STRING_TO_SEARCH = @Value(path_filename)
    MATCHED -> Tester
Tester
    BOOL_OP = OR
    TEST_CLAUSE = TEST @Value(_meshcode) IN 56380589,56380680,56380681,56380598,56380599,56380690,56380691,56381508,56381509,56381600,56381519,56381610
    TEST_MODE = TEST
    PASSED -> FeatureReader [INITIATOR]

Bookmark: 属性抽出
XMLFlattener
    ATTRIBUTE_XML = uro_tran_facility_attribute{0}
    EMBEDDED_EXPRESSIONS = ParkFacilityLongevityPlanAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> XMLFlattener_2
XMLFlattener_2
    ATTRIBUTE_XML = uro_tran_facility_type_attribute{0}
    EMBEDDED_EXPRESSIONS = FacilityTypeAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    XML_SOURCE_TYPE = Attribute with XML document
    -> AttributeExposer_2
AttributeExposer_2
    ATTR_TABLE = facilityId,,function,,specificFacilityName,,mainMaterialOptional,,size,,installationYear,,expectedUsagePeriod,,managementType,,facilityName,
    -> AttributeManager
AttributeManager
    ATTR_TABLE:
      REMOVE uro_tran_facility_attribute{0} (varchar(200))
      REMOVE uro_tran_facility_type_attribute{0} (varchar(200))
      REMOVE uro_tran_facility_attribute{} (varchar(200))
      REMOVE uro_tran_facility_type_attribute{} (varchar(200))
    USER_EXPOSED_ATTRIBUTES = mainMaterial
    -> SchemaMapper
SchemaMapper
    CSV2_CASE_SENSITIVE_FIELD_NAMES = Yes
    CSV2_CHUNK_SIZE = 100000
    CSV2_DATA_START_LINE = 2
    CSV2_DELIMITER = auto
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR)resources\code_value_mapping.csv
    FORMAT = CSV2
    IDXDESTATTR = fme_feature_type
    IDXDESTCOL = ""
    IDXSOURCEATTR = fme_feature_type
    IDXSOURCECOL = ""
    MAP_ATTRS = """""" filter description
    MATCH_ATTRS = filter code
    ROW_ID_ATTR = _schemamapper_row_ids
    TABLE = code_value_mapping
    MAPPED -> Tester_3
Tester_3
    BOOL_OP = OR
    TEST_CLAUSE = TEST @Left(@Value(facilityId),3) IN ENR,SYU,KYU,YUG,UND,KYO,BEN,KAN,SNO
    TEST_MODE = TEST
    PASSED -> FeatureMerger [SUPPLIER]
