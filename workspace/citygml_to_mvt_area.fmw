FME workspace citygml_to_mvt_area.fmw

Parameters:
- SourceDataset_PATH = $(FME_MF_DIR)source\15202_nagaoka-shi_city_2023_citygml_1_op\udx\area   # INCLUDE_WEB_BROWSER 3D都市モデル udx/area フォルダー
- DestDataset_MVT_TILESET = $(FME_MF_DIR)output\mvt\area   # MVT 出力先フォルダー
- DestDataset_OGCGEOPACKAGE = $(FME_MF_DIR)output\footprint.gpkg   # フットプリント出力先 GeoPackage

Readers:
- PATH_1: PATH from $(SourceDataset_PATH)

Writers:
- MVT_TILESET_1: MVT_TILESET to $(DestDataset_MVT_TILESET)
- OGCGEOPACKAGE_1: OGCGEOPACKAGE to $(DestDataset_OGCGEOPACKAGE)

PATH (reader PATH_1)
    attributes: path_unix buffer, path_windows buffer, path_rootname buffer, path_filename buffer, path_extension buffer, path_directory_unix buffer, path_directory_windows buffer, path_type char(10)
    -> StringSearcher
FeatureReader
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 0 1 2 3 4
    CITYGML_MATERIAL_FEATURES = No
    CITYGML_MAX_ATTRIBUTES_PER_NESTED_ATTRIBUTE = 1
    CITYGML_ONLY_FEATURE_TYPES_IN_DATASET = YES
    CITYGML_SKIP_SCHEMA_LOCATION_IN_DATASET = No
    CITYGML_SRS_AXIS_ORDER = 2,1,3
    CITYGML_SUPPORTED_READER_ARCHIVE_EXTENSIONS = xml.gz,gml.gz
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FEATURETYPES = Zone
    FORMAT = CITYGML
    INTERACT = NONE
    ORDER_RESULTS = No
    OUTPUT_FEATURES_DISPLAY = Schema and Data Features
    <OTHER> -> AttributeExposer
AttributeExposer
    ATTR_TABLE = gml_name,,urf_function{0},,urf_function{0}.codeSpace,,urf_location,,urf_nominal_area,,urf_nominal_area_units,,urf_urban_park_attribute,
    -> Tester_2
Tester_2
    BOOL_OP = COMPOSITE
    COMPOSITE_TEST = 1 AND 2
    TEST_CLAUSE:
      TEST @Value(gml_name) = 国営越後丘陵公園
      TEST @Value(urf_urban_park_attribute) TYPE XML
    TEST_MODE = TEST
    PASSED -> XMLFlattener
XMLFlattener
    ATTRIBUTE_XML = urf_urban_park_attribute
    EMBEDDED_EXPRESSIONS = UrbanParkAttribute
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    IGNORE_DATASET_EXTERNAL_DTD = No
    SUB_FRAGMENT_OPTIONS = _area_
    XML_SOURCE_TYPE = Attribute with XML document
    -> AttributeExposer_2
AttributeExposer_2
    ATTR_TABLE = parkCode,,parkCode.codeSpace,,startFrom,,urf_function{0},,urf_location,,urf_nominal_area,,urf_nominal_area_units,
    -> AttributeRenamer
AttributeRenamer
    ATTR_TABLE = RENAME_SET_DEFAULT urf_function{0} > zoneFunction
    MISSING_INPUT_ATTRS = REMOVE
    -> SchemaMapper
SchemaMapper
    CSV2_CASE_SENSITIVE_FIELD_NAMES = Yes
    CSV2_CHUNK_SIZE = 100000
    CSV2_DATA_START_LINE = 2
    CSV2_DELIMITER = ,
    CSV2_DELIMITER_DETECTION_ALGORITHM = EQUAL_FIELDS_PER_LINE
    CSV2_ENCODING = utf-8
    CSV2_ENFORCE_STRICT_SCHEMA = No
    CSV2_FEATURE_TYPE_NAME = FILE_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(FME_MF_DIR)resources\code_value_mapping.csv
    FORMAT = CSV2
    IDXDESTATTR = fme_feature_type
    IDXDESTCOL = ""
    IDXSOURCEATTR = fme_feature_type
    IDXSOURCECOL = ""
    MAP_ATTRS = """""" filter description
    MATCH_ATTRS = filter code
    ROW_ID_ATTR = _schemamapper_row_ids
    TABLE = code_value_mapping
    MAPPED -> AttributeManager
AttributeManager
    ATTR_TABLE:
      SET_TO feature_type (buffer) = Zone
      RENAME_SET_VALUE gml_name > name (buffer)
      RENAME_SET_VALUE zoneFunction > function (varchar(200))
      REMOVE urf_function{0}.codeSpace (varchar(200))
      RENAME_SET_VALUE urf_nominal_area > nominalArea (real64)
      REMOVE urf_nominal_area_units (varchar(200))
      RENAME_SET_VALUE urf_location > location (buffer)
      REMOVE urf_urban_park_attribute (varchar(200))
      REMOVE parkCode (buffer)
      REMOVE startFrom (date)
      REMOVE parkCode.codeSpace (varchar(200))
      REMOVE urf_function{}.codeSpace (varchar(200))
      REMOVE _schemamapper_row_ids (buffer)
    -> 2DForcer
2DForcer
    2D -> CoordinateSystemSetter
CoordinateSystemSetter
    COORDSYS = EPSG:4326
    -> Zone (writer MVT_TILESET_1)
    -> Zone (writer OGCGEOPACKAGE_1)
Zone (writer MVT_TILESET_1)
    attributes: feature_type string, name string, function string, nominalArea double, location string
Zone (writer OGCGEOPACKAGE_1)
    attributes: feature_type text, name text, function text(200), nominalArea double, location text

Bookmark: 越後丘陵公園が含まれる図郭のファイルを抽出
StringSearcher
    CASE = no
    MATCHED_RESULT_ATTR = _meshcode
    REGEXP = ^\d+
    STRING_TO_SEARCH = @Value(path_filename)
    MATCHED -> Tester
Tester
    BOOL_OP = OR
    TEST_CLAUSE = TEST @Value(_meshcode) IN 563805,563806,563815,563816
    TEST_MODE = TEST
    PASSED -> FeatureReader [INITIATOR]
